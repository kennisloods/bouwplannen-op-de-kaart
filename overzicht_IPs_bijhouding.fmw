FME workspace overzicht_IPs_bijhouding.fmw

Parameters:
- P_IP_FGDB = K:\GEODATA\Kennisloods\Data\IP_uitzendingen_overzicht\IP_overzicht.gdb   # File Geodatabase
- P_BRON_TEKENINGPAD = K:\SO\RW\Algemeen\UITZENDINGEN NIEUWE STIJL\1 IP   # Source Folder and File Pathnames Folder
- P_BRON_UITZENDINGEN_XLS = K:\SO\RW\Algemeen\UITZENDINGEN NIEUWE STIJL\1 IP\001 Sjablonen\Schema Voortgang IP def.xlsx   # Source Microsoft Excel File(s)
- P_BRON_UITZENDINGEN_CSV = $(FME_MF_DIR)Schema Voortgang IP def.csv   # Source CSV (Comma Separated Value) File(s)
- P_BRON_TIR_GEMEENTE_SHP = K:\GEODATA\Basisdata\TIR\Data\SHP\Gemeente\Gemeente_vlakken.shp   # Source Esri Shapefile(s)
- P_BRON_GROEN_BGT = K:\GEODATA\Basisdata\BGT\Data\GDB\BGT_Gemeente.gdb   # Geodatabase
- P_BRON_GROEN_BGT_WHERE = FYSIEKVK IN ('loofbos','gemengd bos','naaldbos','heide','struiken','houtwal','duin','grasland overig','moeras','rietland','kwelder','fruitteelt','boomteelt','bouwland','grasland agrarisch','groenvoorziening')   # WHERE Clause
- P_DOEL_UITVAL_FOLDER = K:\GEODATA\Kennisloods\Data\IP_uitzendingen_overzicht\uitval   # Uitvalfolder
- P_DOEL_BACKUP_FOLDER = K:\GEODATA\Kennisloods\Data\IP_uitzendingen_overzicht\backup   # Backupfolder
- P_DOEL_GROEN_CSV = K:\GEODATA\Kennisloods\Data\GroenInBeeld   # Destination CSV (Comma Separated Value) Folder
- P_LOG = $(FME_MF_DIR)log\overzicht_IPs_bijhouding.log   # Log File

Readers:
- PATH_1: PATH from $(P_BRON_TEKENINGPAD)
- ESRISHAPE_1: ESRISHAPE from $(P_BRON_TIR_GEMEENTE_SHP) in EPSG:28992
- XLSXR_1: XLSXR from $(P_BRON_UITZENDINGEN_XLS)
- CSV2_1: CSV2 from $(P_BRON_UITZENDINGEN_CSV)
- GEODATABASE_FILE_1: GEODATABASE_FILE from $(P_IP_FGDB) in EPSG:28992

Writers:
- GEODATABASE_FILE_2: GEODATABASE_FILE to $(P_DOEL_BACKUP_FOLDER) in EPSG:28992
- GEODATABASE_FILE_3: GEODATABASE_FILE to $(P_IP_FGDB) in EPSG:28992
- CSV2_2: CSV2 to $(P_DOEL_GROEN_CSV)
- CSV2_3: CSV2 to $(P_DOEL_UITVAL_FOLDER)

StringPairReplacer_3_OUTPUT: Junction
    -> InlineQuerierTekening [Tekeningenlijst]
    -> FeatureMerger_UitzendingMetTekening [REQUESTOR]
Note: inlezen bestaande gegevens
IP_overzicht (reader GEODATABASE_FILE_1)
    attributes: OBJECTID integer, identificatie guid, gebiedcode char(3), gebiednaam char(500), projectnaam char(100), tekeningnummer char(50), fase smallint, revisie smallint, ontwerper char(100), tekenaar char(100), actueel smallint, ind_klaar smallint, datumUitzending date, vervaldatum date, coordinator char(100), bestandsactualisatie date, tekeningfolder char(500), tekeningPDF char(500), reactiedoc char(500), ind_lichtplan smallint, ind_bordenplan smallint, opmerking char(500), SHAPE_Length double, SHAPE_Area double
    -> IP_overzicht (writer GEODATABASE_FILE_2)
    -> RevisieSetter_bestaandeSet [In]
RevisieSetter_bestaandeSet
    REVISIE = @Value(revisie)
    Uit -> InlineQuerierPotentieelGewijzigd [IP_overzicht]
    Uit -> AttributeKeeper
    Uit -> InlineQuerierTekening [IP_overzicht]
AttributeKeeper
    KEEP_ATTRS = identificatie
    -> FeatureMerger [SUPPLIER]
Note: backup
IP_overzicht (writer GEODATABASE_FILE_2)
    attributes: OBJECTID integer, identificatie guid, gebiedcode char(3), gebiednaam char(500), projectnaam char(100), tekeningnummer char(50), fase smallint, revisie smallint, ontwerper char(100), tekenaar char(100), actueel smallint, ind_klaar smallint, datumUitzending date, vervaldatum date, coordinator char(100), bestandsactualisatie date, tekeningfolder char(500), tekeningPDF char(500), reactiedoc char(500), ind_lichtplan smallint, ind_bordenplan smallint, opmerking char(500), SHAPE_Length double, SHAPE_Area double
Actualiteitsbepaler
    FASE = @Value(fase)
    IND_KLAAR = @Value(ind_klaar)
    REVISIE = @Value(revisie)
    TEKENINGNUMMER = @Value(tekeningnummer)
    Uit -> Tester_IdentificatieNOTHasValue
    <Rejected> -> Junction_13
Note: Heeft identificatie een waarde? / Zo ja: het is een bestaande feature --> UPDATE / als er daadwerkelijk iets is gewijzigd / zo nee: het is een nieuwe feature --> INSERT
Tester_IdentificatieNOTHasValue
    TEST_MODE = Automatic
    TEST_DESCRIPTION = ""
    BOOL_OP = OR
    TEST_CLAUSE = TEST @Value(identificatie) NOT_ATTRIBUTE_HAS_VALUE ""
    PASSED -> RevisieSetter_INS [In]
    FAILED -> Tester
Note: Is 'actueel' gewijzigd? / ja: UPDATE / nee: negeren / Er wordt vanuit gegaan / dat van bestaande features / alleen het kenmerk ' actueel' / kan wijzigen.
Tester
    TEST_MODE = Automatic
    TEST_DESCRIPTION = ""
    BOOL_OP = OR
    TEST_CLAUSE = TEST @Value(actueel) != @Value(_old_actueel)
    PASSED -> FeatureMerger [REQUESTOR]
Note: huidige datum
DateTimeStamper_2
    TIMEZONE = local
    DATETIME_ATTR = bestandsactualisatie
    STAMP_TYPE = date
    -> AttributeRemover_4
AttributeRemover_4
    REMOVE_ATTRS = _old_actueel
    -> AttributeFilter_uitval
AttributeFilter_uitval
    ATTR_VALUES = <Empty>,<Missing>,<Null>,<Unfiltered>,Bij deze uitzending is geen tekening gevonden.,Bij deze uitzending kon geen contour worden gevormd.
    ATTR_NAME = opmerking
    <EMPTY> -> AttributeFilter__lt_EMPTY_gt__-__SMP_overzicht
    <MISSING> -> AttributeFilter__lt_EMPTY_gt__-__SMP_overzicht
    <NULL> -> AttributeFilter__lt_EMPTY_gt__-__SMP_overzicht
    <UNFILTERED> -> AttributeFilter__lt_EMPTY_gt__-__SMP_overzicht
    Bij deze uitzending is geen tekening gevonden. -> FaseRemapper [IN]
    Bij deze uitzending kon geen contour worden gevormd. -> FaseRemapper_2 [IN]
AttributeFilter__lt_EMPTY_gt__-__SMP_overzicht: Junction
    -> IP_overzicht (writer GEODATABASE_FILE_3)
    -> AttributeKeeper_Groen
FaseRemapper
    FASE = @Value(fase)
    UIT -> uitzending_zonder_tekening (writer CSV2_3)
FaseRemapper_2
    FASE = @Value(fase)
    UIT -> uitzending_zonder_contour (writer CSV2_3)
Junction_13
    -> Junction_15

Bookmark: genereren lijst met beschikbare tekeningen
  Per gebiedcode, tekeningnr, fase en revisie wordt een link gegeven naar de folder op de K:\-schijf, de tekening in dwg- en pdf-fromaat, het reactiedocument in pdf-formaat en een indicatie of er een bordenplan resp. lichtplan aanwezig is (in pdf-formaat).
  De bestandsnaam van een tekening moet de tekst 'tek' bevatten, in pdf- en/of dwg-formaat zijn, en de bestandsnaam mag niet bevatten:
  'doorsnede', 'gevel', 'xref', 'profielen', 'overzichtskaart', 'ondergrondse infra', 'details', 'brief', 'beheerparagraaf'.
  De bestandsnaam van een lichtplan moet 'lichtplan' bevatten en in pdf-formaat zijn.
  De bestandsnaam van een bordenplan moet 'bordenplan' bevatten en in pdf-formaat zijn.
  De bestandsnaam van een reactiedocument moet 'reactiedoc' bevatten en in pdf-formaat zijn.
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeKeeper_Path
AttributeKeeper_Path
    KEEP_ATTRS = path_rootname,path_directory_windows,path_extension,path_windows
    -> tekeningMetadaExtractor [In]
Note: Extraheert bij elke tekening: / gebiedscode, / tekeningnummer, / fase, / revisie / uit de naam van de / bovenliggende folderstructuur. / Als er geen revisie wordt gevonden dan / wordt revisie op 1 gezet. / Dit is een aangepaste versie van de / metadataextractor voor de SMP's / (er wordt nu naar de string 'IP'(...) gezocht / om de tekeningnummer te vinden. / Exotische nummeringen worden als volgt / omgecodeerd: / was / wordt / IP12-08-16-RO-Platenbuurt / 12-08-16 / IPs257-123-KC-Omg. Blok F - Park / s257-123 / IPs257-127-KC-Omg. Blok E Catharina van Zoelenstr / s257-127 / IP99-W-1588-HO-Meeuwenplaat-Steurweg / 99-W-1588 / IP92-W-2157-HO-Westpunt Tijmweg en Hofjes / 92-W-2157 / IP92-W-2148-HO-Troubadourlaan-Falstaffstr / 92-W-2148
tekeningMetadaExtractor
    _TEKENINGPAD = @Value(path_windows)
    Uit -> Tester_metadataHasValue
    _Rejected_ -> Junction
Note: uitfilteren PVE's
Tester_metadataHasValue
    TEST_MODE = Automatic
    TEST_DESCRIPTION = ""
    BOOL_OP = AND
    TEST_CLAUSE:
      TEST @Value(_gebiedcode) ATTRIBUTE_HAS_VALUE ""
      TEST @Value(_tekeningnummer) ATTRIBUTE_HAS_VALUE ""
      TEST @Value(_fase) ATTRIBUTE_HAS_VALUE ""
      TEST @Value(_revisie) ATTRIBUTE_HAS_VALUE ""
    PASSED -> StringSearcher_Reactiedoc
Note: Selecteren van bestanden / met in de naam: / Reactiedoc
StringSearcher_Reactiedoc
    CASE = no
    REGEXP = Reactiedoc
    STRING_TO_SEARCH = @Value(path_rootname)
    MATCHED_RESULT_ATTR = _first_match
    MATCHED -> StringCaseChanger_Path_extension_reactiedoc
    NOT_MATCHED -> StringSearcherBordenplan
Note: Selecteren van bestanden / met in de naam: / Bordenplan
StringSearcherBordenplan
    CASE = no
    REGEXP = Bordenplan
    STRING_TO_SEARCH = @Value(path_rootname)
    MATCHED_RESULT_ATTR = _first_match
    MATCHED -> StringCaseChanger_Path_extension_bordenplan
    NOT_MATCHED -> StringSearcherLichtplan
Note: Selecteren van bestanden / met in de naam: / Lichtplan
StringSearcherLichtplan
    CASE = no
    REGEXP = Lichtplan
    STRING_TO_SEARCH = @Value(path_rootname)
    MATCHED_RESULT_ATTR = _first_match
    MATCHED -> StringCaseChanger_Path_extension_lichtplan
    NOT_MATCHED -> StringSearcher_gevel_doorsnede
Note: Voorfilter:Wegfilteren van / bestanden met in de naam: / doorsnede / gevel / xref / Profielen / overzichtskaart / dwarsprofielen / ondergrondse infra / details / brief / Beheerparagraaf
StringSearcher_gevel_doorsnede
    CASE = no
    REGEXP = doorsnede|gevel|xref|Profielen|overzichtskaart|dwarsprofielen|ondergrondse infra|details|brief|Beheerparagraaf
    STRING_TO_SEARCH = @Value(path_rootname)
    MATCHED_RESULT_ATTR = _first_match
    NOT_MATCHED -> StringSearcherTek [off]
    NOT_MATCHED -> StringSearcher_revisie_2
StringSearcherTek [off]
    CASE = no
    REGEXP = tek
    STRING_TO_SEARCH = @Value(path_rootname)
    MATCHED -> StringSearcher_revisie_2 [off]
Note: in tekeningnummer '-' vervangen / door '/' / bijv. 18-00046 wordt 18/00046
StringPairReplacer_3
    MAP = - /
    RESULT_ATTR = _tekeningnummer
    CASE = no
    SRC_ATTR = _tekeningnummer
    -> StringPairReplacer_3_OUTPUT
Junction
    -> Junction_2

Bookmark: ophalen van de link naar het reactiedocument (in pdf-formaat)
StringCaseChanger_Path_extension_reactiedoc
    ATTRCHOICE = Selected Attributes
    ATTRLIST = path_extension
    CHANGE_TYPE = lowercase
    -> Tester_pdf_reactiedoc
Note: alleen reactiedocumenten in / pdf-formaat worden verwerkt.
Tester_pdf_reactiedoc
    TEST_MODE = Automatic
    TEST_DESCRIPTION = ""
    BOOL_OP = OR
    TEST_CLAUSE = TEST @Value(path_extension) = pdf
    PASSED -> DuplicateFilter_reactiedoc
DuplicateFilter_reactiedoc
    KEYATTR = _gebiedcode _revisie _tekeningnummer _fase
    INPUT_ORDERED_CHOICE = No
    UNIQUE -> AttributeManager_Path_pdf_reactiedoc
Note: _reactiedoc := path_windows
AttributeManager_Path_pdf_reactiedoc
    ATTR_TABLE:
      REMOVE path_directory_windows
      RENAME_SET_VALUE path_windows > _reactiedoc
      REMOVE path_extension
      REMOVE path_rootname
      REMOVE _first_match
    -> FeatureMerger_reactiedocument [SUPPLIER]

Bookmark: bepalen van de aanwezigheid van een bordenplan
StringCaseChanger_Path_extension_bordenplan
    ATTRCHOICE = Selected Attributes
    ATTRLIST = path_extension
    CHANGE_TYPE = lowercase
    -> Tester_pdf_bordenplan
Note: alleen bordenplannen in / pdf-formaat worden verwerkt.
Tester_pdf_bordenplan
    TEST_MODE = Automatic
    TEST_DESCRIPTION = ""
    BOOL_OP = OR
    TEST_CLAUSE = TEST @Value(path_extension) = pdf
    PASSED -> DuplicateFilter_bordenplan
DuplicateFilter_bordenplan
    KEYATTR = _gebiedcode _revisie _tekeningnummer _fase
    INPUT_ORDERED_CHOICE = No
    UNIQUE -> AttributeManager_ind_bordenplan
Note: _ind_bordenplan := 1
AttributeManager_ind_bordenplan
    ATTR_TABLE:
      REMOVE path_directory_windows
      REMOVE path_windows
      REMOVE path_extension
      REMOVE path_rootname
      REMOVE _first_match
      SET_TO _ind_bordenplan = 1
    -> FeatureMerger_bordenplan [SUPPLIER]

Bookmark: bepalen van de aanwezigheid van een lichtplan
StringCaseChanger_Path_extension_lichtplan
    ATTRCHOICE = Selected Attributes
    ATTRLIST = path_extension
    CHANGE_TYPE = lowercase
    -> Tester_pdf_lichtplan
Note: alleen bordenplannen in / pdf-formaat worden verwerkt.
Note: Bevat bestandsnaam de / string 'tek'? / ook tekeningen zoals 'dwg GUZ.dwg' / vallen hiermee weg. / uitgschakeld omdat de meeste tekeningen / niet aan deze conventie voldoen
Tester_pdf_lichtplan
    TEST_MODE = Automatic
    TEST_DESCRIPTION = ""
    BOOL_OP = OR
    TEST_CLAUSE = TEST @Value(path_extension) = pdf
    PASSED -> DuplicateFilter_lichtplan
DuplicateFilter_lichtplan
    KEYATTR = _gebiedcode _revisie _tekeningnummer _fase
    INPUT_ORDERED_CHOICE = No
    UNIQUE -> AttributeManager_ind_lichtplan
Note: _ind_lichtplan := 1
AttributeManager_ind_lichtplan
    ATTR_TABLE:
      REMOVE path_directory_windows
      REMOVE path_windows
      REMOVE path_extension
      REMOVE path_rootname
      REMOVE _first_match
      SET_TO _ind_lichtplan = 1
    -> FeatureMerger_lichtplan [SUPPLIER]

Bookmark: corrigeren revisie bij VUZ, GUZ, DUZ, WUZ
  Revisies hebben in principe in de nieuwe stijl een aparte map. Soms staan er echter revisies bij elkaar in 1 map.
  Als de bestandsnaam een revisienummer bevat dan wordt hier de revisie daarop aangepast.
StringSearcher_revisie_2
    MATCHED_PARTS_ATTR = _subexp
    CASE = no
    REGEXP = [VGDW]UZ\s?(\d)
    STRING_TO_SEARCH = @Value(path_rootname)
    MATCHED -> ListIndexer
    NOT_MATCHED -> AttributeRemover_3
ListIndexer
    LIST_ATTR = _subexp{}
    INDEX = 0
    -> AttributeCreator_revisie
    <REJECTED> -> Junction_5
AttributeCreator_revisie
    ATTR_TABLE = SET_TO _revisie = @Value(part)
    -> AttributeRemover_3
AttributeRemover_3
    REMOVE_ATTRS = path_rootname,startIndex,part
    LIST_ATTRS = _subexp{}
    -> StringCaseChanger_Path_extension
Junction_5
    -> Junction_6

Bookmark: uitsplitsen pdf / dwg en verwijderen dubbele tekeningen
StringCaseChanger_Path_extension
    ATTRCHOICE = Selected Attributes
    ATTRLIST = path_extension
    CHANGE_TYPE = lowercase
    -> AttributeFilter_Path_extension
AttributeFilter_Path_extension
    ATTR_VALUES = <Empty>,<Missing>,<Null>,<Unfiltered>,dwg,pdf
    ATTR_NAME = path_extension
    dwg -> AttributeManager_Path_dwg
    pdf -> AttributeManager_Path_pdf
AttributeManager_Path_dwg
    ATTR_TABLE:
      RENAME_SET_VALUE path_directory_windows > _tekeningfolder
      RENAME_SET_VALUE path_windows > _tekeningpad
      REMOVE path_extension
    -> DuplicateFilter_dwg
DuplicateFilter_dwg
    KEYATTR = _fase _revisie _gebiedcode _tekeningnummer
    INPUT_ORDERED_CHOICE = No
    UNIQUE -> FeatureMerger_2 [REQUESTOR]
AttributeManager_Path_pdf
    ATTR_TABLE:
      REMOVE path_directory_windows
      RENAME_SET_VALUE path_windows > _tekeningPDF
      REMOVE path_extension
    -> DuplicateFilter_pdf
DuplicateFilter_pdf
    KEYATTR = _fase _revisie _gebiedcode _tekeningnummer
    INPUT_ORDERED_CHOICE = No
    UNIQUE -> FeatureMerger_2 [SUPPLIER]
Note: Left outer join pdf - dwg
FeatureMerger_2
    SUPPLIERS_FIRST = No
    JOIN_KEYS = @Value(_gebiedcode) @Value(_gebiedcode) AUTO @Value(_tekeningnummer) @Value(_tekeningnummer) AUTO @Value(_fase) @Value(_fase) AUTO @Value(_revisie) @Value(_revisie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_UNUSED_SUPPLIER_-__FeatureMerger_UnusedSupplier
    UNMERGED_REQUESTOR -> FeatureMerger_UNUSED_SUPPLIER_-__FeatureMerger_UnusedSupplier
    UNUSED_SUPPLIER -> FeatureMerger_UNUSED_SUPPLIER_-__FeatureMerger_UnusedSupplier
    <REJECTED> -> Junction_3
FeatureMerger_UNUSED_SUPPLIER_-__FeatureMerger_UnusedSupplier: Junction
    -> FeatureMerger_lichtplan [REQUESTOR]
Junction_3

Bookmark: join met lichtplan, bordenplan en reactiedocument
Note: full outer join tekening-lichtplan
FeatureMerger_lichtplan
    SUPPLIERS_FIRST = No
    JOIN_KEYS = @Value(_gebiedcode) @Value(_gebiedcode) AUTO @Value(_tekeningnummer) @Value(_tekeningnummer) AUTO @Value(_fase) @Value(_fase) AUTO @Value(_revisie) @Value(_revisie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_5_MERGED
    UNMERGED_REQUESTOR -> FeatureMerger_5_MERGED
    UNUSED_SUPPLIER -> FeatureMerger_5_MERGED
    <REJECTED> -> Junction_18
FeatureMerger_5_MERGED: Junction
    -> FeatureMerger_bordenplan [REQUESTOR]
Note: full outer join tekening-bordenplan
FeatureMerger_bordenplan
    SUPPLIERS_FIRST = No
    JOIN_KEYS = @Value(_gebiedcode) @Value(_gebiedcode) AUTO @Value(_tekeningnummer) @Value(_tekeningnummer) AUTO @Value(_fase) @Value(_fase) AUTO @Value(_revisie) @Value(_revisie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_3_MERGED
    UNMERGED_REQUESTOR -> FeatureMerger_3_MERGED
    UNUSED_SUPPLIER -> FeatureMerger_3_MERGED
    <REJECTED> -> Junction_10
FeatureMerger_3_MERGED: Junction
    -> FeatureMerger_reactiedocument [REQUESTOR]
Note: full outer join tekening - reactiedocument
FeatureMerger_reactiedocument
    SUPPLIERS_FIRST = No
    JOIN_KEYS = @Value(_gebiedcode) @Value(_gebiedcode) AUTO @Value(_tekeningnummer) @Value(_tekeningnummer) AUTO @Value(_fase) @Value(_fase) AUTO @Value(_revisie) @Value(_revisie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_4_MERGED
    UNMERGED_REQUESTOR -> FeatureMerger_4_MERGED
    UNUSED_SUPPLIER -> FeatureMerger_4_MERGED
    <REJECTED> -> Junction_8
FeatureMerger_4_MERGED: Junction
    -> StringPairReplacer_3
Junction_8
Junction_10
    -> Junction_11
Junction_18
    -> Junction_19

Bookmark: uitval
Junction_11
    -> _Rejected_
Junction_19
    -> _Rejected_
Junction_6
    -> _Rejected_
Junction_2
    -> _Rejected_
Junction_17
    -> _Rejected_
Junction_7
    -> _Rejected_
Junction_21
    -> _Rejected_
Junction_15
    -> _Rejected_
Junction_14
    -> _Rejected_
_Rejected_: Logger
    MAXFEATS = 20
    MESSAGE = Feature is:
    MAXCOORDS = 20

Bookmark: Inlezen uitzendlijst in CSV-formaat
  Versie 2017.1 geeft soms een foutmelding bij het inlezen van een excel-bestand (in xlsx-indeling).
  De volgende foutmelding treedt dan op:
  Excel Reader: Could not open file 'K:\SO\RW\Algemeen\UITZENDINGEN NIEUWE STIJL\2 SMP\001 Sjablonen\Schema Voortgang SMP def.xlsx', file is too large. Try switching to 64-bit FME, or exporting the Excel file to CSV. (...)
  De workaround is: 
  1. kopieer het excelbestand naar een csv-bestand 
      (K:\GEODATA\Kennisloods\Beheer\Uitzendingen_overzicht\Schema Voortgang IO def.csv)
  2. schakel de excel-reader uit 
       ('Schema Voortgang IP def [XLSXR]')
  3. schakel de csv-reader in 
      ('Schema Voortgang IP def [CSV2]')
  4. voer het script uit
Schema Voortgang IP def (reader CSV2_1)
    attributes: col0 string, col1 string, col2 string, col3 string, col4 string, col5 string, col6 string, col7 string, col8 string, col9 string, col10 string, col11 string, col12 string, col13 string, col14 string, col15 string, col16 string, col17 string, col18 string, col19 string, col20 string, col21 string, col22 string, col23 string, col24 string, col25 string, col26 string, col27 string, col28 string, col29 string,
      col30 string, col31 string, col32 string, col33 string, col34 string
    -> Tester_tekeningnummerHasValueCSV
Note: wegfilteren lege rijen / en / rijen die niet met de volgende reguliere / expressie beginnen: ^\d{2}-\d{5}$
Tester_tekeningnummerHasValueCSV
    TEST_MODE = Automatic
    TEST_DESCRIPTION = ""
    BOOL_OP = AND
    TEST_CLAUSE:
      TEST @Value(col0) ATTRIBUTE_HAS_VALUE ""
      TEST @Value(col0) CONTAINS_REGEX ^\d{2}-\d{5}$
    PASSED -> AttributeManager_Uitzendlijst_CSV
    PASSED -> StatisticsCalculator_CSV
AttributeManager_Uitzendlijst_CSV
    ATTR_TABLE:
      REMOVE fme_feature_type
      RENAME_SET_VALUE col0 > IPnummer
      RENAME_SET_VALUE col1 > gebiedcode
      RENAME_SET_VALUE col2 > locatie
      RENAME_SET_VALUE col3 > ontwerper
      RENAME_SET_VALUE col4 > tekenaar
      RENAME_SET_VALUE col5 > coordinator
      RENAME_SET_VALUE col6 > Verzenddatum_PvE1
      RENAME_SET_VALUE col7 > Vervaldatum_PvE1
      REMOVE col8
      RENAME_SET_VALUE col9 > Verzenddatum_PvE2
      RENAME_SET_VALUE col10 > vervaldatum_PvE2
      REMOVE col11
      RENAME_SET_VALUE col12 > Verzenddatum_PvE3
      RENAME_SET_VALUE col13 > vervaldatum_PvE3
      REMOVE col14
      RENAME_SET_VALUE col15 > Verzenddatum_VUZ
      RENAME_SET_VALUE col16 > vervaldatum_VUZ
      REMOVE col17
      RENAME_SET_VALUE col18 > Verzenddatum_GUZ
      RENAME_SET_VALUE col19 > vervaldatum_GUZ
      REMOVE col20
      RENAME_SET_VALUE col21 > Verzenddatum_DUZ
      RENAME_SET_VALUE col22 > vervaldatum_DUZ
      REMOVE col23
      RENAME_SET_VALUE col24 > Verzenddatum_WUZ
      REMOVE col25
      RENAME_SET_VALUE col26 > _klaar
      REMOVE col27
      REMOVE col28
      REMOVE col29
      REMOVE col30
      REMOVE col31
      REMOVE col32
      REMOVE col33
      REMOVE col34
    -> NullAttributeMapper
NullAttributeMapper
    NULL_TREATMENT = Null
    ATTRCHOICE = Selected Attributes
    SOURCE_ATTR_VAL = Empty "Missing (Selected Attributes Only)"
    ATTRLIST = Verzenddatum_VUZ Verzenddatum_DUZ IPnummer coordinator tekenaar Vervaldatum_PvE1 Verzenddatum_PvE2 vervaldatum_GUZ vervaldatum_PvE2 locatie vervaldatum_PvE3 Verzenddatum_GUZ gebiedcode Verzenddatum_PvE1 vervaldatum_DUZ vervaldatum_VUZ ontwerper _klaar Verzenddatum_WUZ Verzenddatum_PvE3
    -> Tester_klaarHasValue

Bookmark: testen of de uitzenindingen niet tegelijk in CSV-formaat en in Excel-formaat worden ingelezen.
StatisticsCalculator_CSV
    COUNT_ATTR = _countCSV
    COMPUTE_HISTOGRAM = NO
    PREPEND_ATTR_NAME_CHOICE = For multiple results only
    STATS_ATTRS = fme_feature_type
    SUMMARY -> Tester_aantalUItzendingen
StatisticsCalculator_XLSX
    COUNT_ATTR = _countXLSX
    COMPUTE_HISTOGRAM = NO
    PREPEND_ATTR_NAME_CHOICE = For multiple results only
    STATS_ATTRS = fme_feature_type
    SUMMARY -> Tester_aantalUItzendingen
Note: Het script wordt afgebroken / als de uitzendingen zowel in / CSV-formaat als in Excel-formaat / worden ingelezen.
Tester_aantalUItzendingen
    TEST_MODE = Automatic
    TEST_DESCRIPTION = ""
    BOOL_OP = OR
    TEST_CLAUSE:
      TEST @Value(_countXLSX) = @Evaluate(@Value(_countCSV)+@Value(_countXLSX))
      TEST @Value(_countCSV) = @Evaluate(@Value(_countCSV)+@Value(_countXLSX))
    FAILED -> Terminator_2
Terminator_2
    MESSAGE = De uitzendingenlijst wordt zowel in CSV- als in Excelformaat ingelezen. Schakel een van beide uit.

Bookmark: inlezen uitzendlijst in excel-formaat
Note: inlezen uitzendingenlijst: / Schema Voortgang IP def.xls / tabblad: Voortgang IP's
Voortgang IP's (reader XLSXR_1)
    attributes: IP- of tekeningnr char(138), Gebied char(4), Locatie char(52), Ontwerper char(15), Tekenaar char(10), Gebiedscoordinator/-commissie _of bestuurlijk char(16), Verzenddatum_PvE1 date, Vervaldatum_PvE1 _(30 wrkdgn) date, PvE1 number(2,0), Verzenddatum_PvE2 date, vervaldatum_PvE2 _(5 wrkdgn) date, PvE2 number(2,0), Verzenddatum_PvE3 string, vervaldatum_PvE3 _(30 wrkdgn) date, PvE3 number(2,0), Verzenddatum_VUZ date, vervaldatum_VUZ _(30 wrkdgn) date, VUZ number(2,0), Verzenddatum_GUZ string, vervaldatum_GUZ _(5 wrkdgn) date, GUZ number(2,0), Verzenddatum_DUZ date, vervaldatum_DUZ _(30 wrkdgn) date, DUZ number(2,0), Verzenddatum_WUZ date, WUZ number(2,0), Klaar? char(2), Doorlooptijd in dagen tot vandaag number(6,0), Opmerkingen bij deze IP: char(35), AD string,
      AE string, AF string, VANDAAG date, AANTAL WERKDAGEN number(3,0), AANTAL WERKDAGEN00 number(2,0)
    -> Tester_tekeningnummerHasValue
Note: wegfilteren lege / rijen
Tester_tekeningnummerHasValue
    TEST_MODE = Automatic
    TEST_DESCRIPTION = ""
    BOOL_OP = AND
    TEST_CLAUSE:
      TEST @Value(IP- of tekeningnr) ATTRIBUTE_HAS_VALUE ""
      TEST @Value(IP- of tekeningnr) NOT_BEGINS_WITH Geen regels genoeg
    PASSED -> AttributeManager_Uitzendlijst
    PASSED -> StatisticsCalculator_XLSX
AttributeManager_Uitzendlijst
    ATTR_TABLE:
      RENAME_SET_VALUE IP- of tekeningnr > IPnummer
      RENAME_SET_VALUE Gebied > gebiedcode
      RENAME_SET_VALUE Locatie > locatie
      RENAME_SET_VALUE Ontwerper > ontwerper
      RENAME_SET_VALUE Tekenaar > tekenaar
      RENAME_SET_VALUE Gebiedscoordinator/-commissie _of bestuurlijk > coordinator
      REMOVE VUZ
      RENAME_SET_VALUE vervaldatum_GUZ _(5 wrkdgn) > vervaldatum_GUZ
      REMOVE GUZ
      REMOVE DUZ
      REMOVE WUZ
      REMOVE Doorlooptijd in dagen tot vandaag
      REMOVE Opmerkingen bij deze IP:
      REMOVE VANDAAG
      REMOVE AANTAL WERKDAGEN
      REMOVE AANTAL WERKDAGEN00
      REMOVE AD
      REMOVE AE
      RENAME_SET_VALUE Vervaldatum_PvE1 _(30 wrkdgn) > Vervaldatum_PvE1
      REMOVE PvE1
      RENAME_SET_VALUE vervaldatum_PvE2 _(5 wrkdgn) > vervaldatum_PvE2
      REMOVE PvE2
      RENAME_SET_VALUE vervaldatum_PvE3 _(30 wrkdgn) > vervaldatum_PvE3
      REMOVE PvE3
      RENAME_SET_VALUE vervaldatum_VUZ _(30 wrkdgn) > vervaldatum_VUZ
      RENAME_SET_VALUE vervaldatum_DUZ _(30 wrkdgn) > vervaldatum_DUZ
      RENAME_SET_VALUE Klaar? > _klaar
      REMOVE AF
      REMOVE fme_feature_type
    -> Tester_klaarHasValue

Bookmark: ind_klaar
Tester_klaarHasValue
    TEST_MODE = Automatic
    TEST_DESCRIPTION = ""
    BOOL_OP = OR
    TEST_CLAUSE = TEST @Value(_klaar) ATTRIBUTE_HAS_VALUE ""
    PASSED -> AttributeCreator
    FAILED -> AttributeCreator_2
AttributeCreator
    ATTR_TABLE = SET_TO ind_klaar = 1
    -> AttributeCreator_2_OUTPUT
AttributeCreator_2
    ATTR_TABLE = SET_TO ind_klaar = 0
    -> AttributeCreator_2_OUTPUT
AttributeCreator_2_OUTPUT: Junction
    -> AttributeValueMapper_3

Bookmark: ophalen metagegevens uitzendingen nieuwe stijl
Note: IJS wordt YS
AttributeValueMapper_3
    DEFAULT_VALUE = @Value(gebiedcode)
    VAL_ATTR = gebiedcode
    LUT = IJS,YS
    DIRECTION = Forward (Source To Destination)
    SRC = gebiedcode
    -> StringPairReplacer
Note: in tekeningnummer '-' vervangen / door '/' / bijv. 18-00046 wordt 18/00046
StringPairReplacer
    MAP = - /
    RESULT_ATTR = IPnummer
    CASE = no
    SRC_ATTR = IPnummer
    -> StringPairReplacer_OUTPUT_-__Tester_VerzenddatumVUZHasValue
    -> StringPairReplacer_OUTPUT_-__Tester_VerzenddatumPVE1_HasValue
AttributeManager_2
    -> InlineQuerierTekening [Uitzendingenlijst]

Bookmark: bepalen fase + datumuitzending
StringPairReplacer_OUTPUT_-__Tester_VerzenddatumVUZHasValue: Junction
    -> Tester_VerzenddatumVUZHasValue
    -> Tester_VerzenddatumGUZHasValue
    -> Tester_VerzenddatumDUZHasValue
    -> Tester_VerzenddatumWUZHasValue
Tester_VerzenddatumVUZHasValue
    TEST_MODE = Automatic
    TEST_DESCRIPTION = ""
    BOOL_OP = OR
    TEST_CLAUSE = TEST @Value(Verzenddatum_VUZ) ATTRIBUTE_HAS_VALUE ""
    PASSED -> AttributeManager_VUZ
AttributeManager_VUZ
    ATTR_TABLE:
      RENAME_SET_VALUE Verzenddatum_VUZ > datumUitzending
      REMOVE Verzenddatum_GUZ
      REMOVE Verzenddatum_DUZ
      REMOVE Verzenddatum_WUZ
      SET_TO fase = 2
      REMOVE Verzenddatum_PvE1
      REMOVE Verzenddatum_PvE2
      REMOVE Verzenddatum_PvE3
      REMOVE vervaldatum_GUZ
      REMOVE Vervaldatum_PvE1
      REMOVE vervaldatum_PvE2
      REMOVE vervaldatum_PvE3
      RENAME_SET_VALUE vervaldatum_VUZ > vervaldatum
      REMOVE vervaldatum_DUZ
    -> AttributeManager_VUZ_OUTPUT
Tester_VerzenddatumGUZHasValue
    TEST_MODE = Automatic
    TEST_DESCRIPTION = ""
    BOOL_OP = OR
    TEST_CLAUSE = TEST @Value(Verzenddatum_GUZ) ATTRIBUTE_HAS_VALUE ""
    PASSED -> AttributeManager_GUZ
AttributeManager_GUZ
    ATTR_TABLE:
      REMOVE Verzenddatum_VUZ
      RENAME_SET_VALUE Verzenddatum_GUZ > datumUitzending
      REMOVE Verzenddatum_DUZ
      REMOVE Verzenddatum_WUZ
      SET_TO fase = 4
      REMOVE Verzenddatum_PvE1
      REMOVE Verzenddatum_PvE2
      REMOVE Verzenddatum_PvE3
      RENAME_SET_VALUE vervaldatum_GUZ > vervaldatum
      REMOVE Vervaldatum_PvE1
      REMOVE vervaldatum_PvE2
      REMOVE vervaldatum_PvE3
      REMOVE vervaldatum_VUZ
      REMOVE vervaldatum_DUZ
    -> AttributeManager_VUZ_OUTPUT
Tester_VerzenddatumDUZHasValue
    TEST_MODE = Automatic
    TEST_DESCRIPTION = ""
    BOOL_OP = OR
    TEST_CLAUSE = TEST @Value(Verzenddatum_DUZ) ATTRIBUTE_HAS_VALUE ""
    PASSED -> AttributeManager_DUZ
AttributeManager_DUZ
    ATTR_TABLE:
      REMOVE Verzenddatum_VUZ
      REMOVE Verzenddatum_GUZ
      RENAME_SET_VALUE Verzenddatum_DUZ > datumUitzending
      REMOVE Verzenddatum_WUZ
      SET_TO fase = 5
      REMOVE Verzenddatum_PvE1
      REMOVE Verzenddatum_PvE2
      REMOVE Verzenddatum_PvE3
      REMOVE vervaldatum_GUZ
      REMOVE Vervaldatum_PvE1
      REMOVE vervaldatum_PvE2
      REMOVE vervaldatum_PvE3
      REMOVE vervaldatum_VUZ
      RENAME_SET_VALUE vervaldatum_DUZ > vervaldatum
    -> AttributeManager_VUZ_OUTPUT
Tester_VerzenddatumWUZHasValue
    TEST_MODE = Automatic
    TEST_DESCRIPTION = ""
    BOOL_OP = OR
    TEST_CLAUSE = TEST @Value(Verzenddatum_WUZ) ATTRIBUTE_HAS_VALUE ""
    PASSED -> AttributeManager_WUZ
AttributeManager_WUZ
    ATTR_TABLE:
      REMOVE Verzenddatum_VUZ
      REMOVE Verzenddatum_GUZ
      REMOVE Verzenddatum_DUZ
      RENAME_SET_VALUE Verzenddatum_WUZ > datumUitzending
      SET_TO fase = 6
      REMOVE Verzenddatum_PvE1
      REMOVE Verzenddatum_PvE2
      REMOVE Verzenddatum_PvE3
      REMOVE vervaldatum_GUZ
      REMOVE Vervaldatum_PvE1
      REMOVE vervaldatum_PvE2
      REMOVE vervaldatum_PvE3
      REMOVE vervaldatum_VUZ
      REMOVE vervaldatum_DUZ
      SET_TO vervaldatum = FME_NULL_VALUE
    -> AttributeManager_VUZ_OUTPUT
AttributeManager_VUZ_OUTPUT: Junction
    -> AttributeManager_2

Bookmark: bepalen fase bij PVE's.
  Wordt ni nog genegeerd
StringPairReplacer_OUTPUT_-__Tester_VerzenddatumPVE1_HasValue: Junction [off]
    -> Tester_VerzenddatumPVE1_HasValue [off]
    -> Tester_VerzenddatumPVE2_HasValue [off]
    -> Tester_VerzenddatumPVE3_HasValue [off]
Tester_VerzenddatumPVE1_HasValue [off]
    TEST_MODE = Automatic
    TEST_DESCRIPTION = ""
    BOOL_OP = OR
    TEST_CLAUSE = TEST @Value(Verzenddatum_PvE1) ATTRIBUTE_HAS_VALUE ""
    PASSED -> AttributeManager_PVE1 [off]
AttributeManager_PVE1 [off]
    ATTR_TABLE:
      REMOVE Verzenddatum_VUZ
      REMOVE Verzenddatum_GUZ
      REMOVE Verzenddatum_DUZ
      REMOVE Verzenddatum_WUZ
      SET_TO fase = 1
      RENAME_SET_VALUE Verzenddatum_PvE1 > datumUitzending
      REMOVE Verzenddatum_PvE2
      REMOVE Verzenddatum_PvE3
      SET_TO revisie = 1
      REMOVE vervaldatum_GUZ
      RENAME_SET_VALUE Vervaldatum_PvE1 > vervaldatum
      REMOVE vervaldatum_PvE2
      REMOVE vervaldatum_PvE3
      REMOVE vervaldatum_VUZ
      REMOVE vervaldatum_DUZ
    -> AttributeManager_PVE1_OUTPUT [off]
Tester_VerzenddatumPVE2_HasValue [off]
    TEST_MODE = Automatic
    TEST_DESCRIPTION = ""
    BOOL_OP = OR
    TEST_CLAUSE = TEST @Value(Verzenddatum_PvE2) ATTRIBUTE_HAS_VALUE ""
    PASSED -> AttributeManager_PVE2 [off]
AttributeManager_PVE2 [off]
    ATTR_TABLE:
      REMOVE Verzenddatum_VUZ
      REMOVE Verzenddatum_GUZ
      REMOVE Verzenddatum_DUZ
      REMOVE Verzenddatum_WUZ
      SET_TO fase = 1
      REMOVE Verzenddatum_PvE1
      RENAME_SET_VALUE Verzenddatum_PvE2 > datumUitzending
      REMOVE Verzenddatum_PvE3
      SET_TO revisie = 2
      REMOVE vervaldatum_GUZ
      REMOVE Vervaldatum_PvE1
      RENAME_SET_VALUE vervaldatum_PvE2 > vervaldatum
      REMOVE vervaldatum_PvE3
      REMOVE vervaldatum_VUZ
      REMOVE vervaldatum_DUZ
    -> AttributeManager_PVE1_OUTPUT [off]
Tester_VerzenddatumPVE3_HasValue [off]
    TEST_MODE = Automatic
    TEST_DESCRIPTION = ""
    BOOL_OP = OR
    TEST_CLAUSE = TEST @Value(Verzenddatum_PvE3) ATTRIBUTE_HAS_VALUE ""
    PASSED -> AttributeManager_PVE3 [off]
AttributeManager_PVE3 [off]
    ATTR_TABLE:
      REMOVE Verzenddatum_VUZ
      REMOVE Verzenddatum_GUZ
      REMOVE Verzenddatum_DUZ
      REMOVE Verzenddatum_WUZ
      SET_TO fase = 1
      REMOVE Verzenddatum_PvE1
      REMOVE Verzenddatum_PvE2
      RENAME_SET_VALUE Verzenddatum_PvE3 > datumUitzending
      SET_TO revisie = 3
      REMOVE vervaldatum_GUZ
      REMOVE Vervaldatum_PvE1
      REMOVE vervaldatum_PvE2
      RENAME_SET_VALUE vervaldatum_PvE3 > vervaldatum
      REMOVE vervaldatum_VUZ
      REMOVE vervaldatum_DUZ
    -> AttributeManager_PVE1_OUTPUT [off]
AttributeManager_PVE1_OUTPUT: Junction [off]

Bookmark: mutatiedetectie
Note: NieuweTekFase: tekeningnummer en/of / tekeningnummer + fase zijn nieuw / NieuweRevisie: tekeningnummer en fase komen in / de uitzendingenlijst en in IP_overzicht voor, maar / in de tekeningenlijst komt een nieuwe revisie voor. / BestaandAfgesloten: tekeningnummer komt voor en / is actueel terwijl de uitzending is afgerond. Deze features / zijn altijd een UPDATE.
InlineQuerierTekening
    QUERY_DEF:
      NieuwTekFase,SELECT new."gebiedcode"
      ,      new."IPnummer"           AS tekeningnummer
      ,      new."fase"
      ,      new."datumUitzending"
      ,      new."vervaldatum"
      ,      new."locatie"            AS projectnaam
      ,      new."coordinator"
      ,      new."ontwerper"
      ,      new."tekenaar"
      ,      new."ind_klaar"
      FROM  "Uitzendingenlijst" AS new
      WHERE NOT EXISTS ( SELECT 'x'
                         FROM   "IP_overzicht" AS old
                         WHERE   new."gebiedcode" = old."gebiedcode"
                         AND     new."IPnummer" = old."tekeningnummer"
                         AND     new."fase" = old."fase"
                       )
      ;,FIRST,NieuweRevisie,SELECT tek."_tekeningpad"       AS _tekeningpad
      ,      tek."_tekeningfolder"    AS _tekeningfolder
      ,      tek."_tekeningPDF"       AS _tekeningPDF
      ,      tek."_reactiedoc"        AS _reactiedoc
      ,      tek."_ind_bordenplan"    AS _ind_bordenplan
      ,      tek."_ind_lichtplan"     AS _ind_lichtplan
      ,      tek."_revisie"           AS revisie
      ,      new."gebiedcode"         AS gebiedcode
      ,      new."IPnummer"           AS tekeningnummer
      ,      new."fase"               AS fase
      ,      new."datumUitzending"    AS datumUitzending
      ,      new."vervaldatum"        AS vervaldatum
      ,      new."locatie"            AS projectnaam
      ,      new."coordinator"        AS coordinator
      ,      new."ontwerper"          AS ontwerper
      ,      new."tekenaar"           AS tekenaar
      ,      new."ind_klaar"          AS ind_klaar
      FROM   Tekeningenlijst   AS tek
      ,      Uitzendingenlijst AS new
      WHERE  new."gebiedcode" = tek."_gebiedcode"
      AND    new."IPnummer"   = tek."_tekeningnummer"
      AND    new."fase"       = tek."_fase"
      AND    EXISTS     ( SELECT 'x'
                          FROM    IP_overzicht AS old
      				    WHERE   old."gebiedcode"     = tek."_gebiedcode"
                          AND     old."tekeningnummer" = tek."_tekeningnummer"
                          AND     old."fase"           = tek."_fase"
      				   )
      AND    NOT EXISTS ( SELECT 'x'
                          FROM    IP_overzicht AS old
      				    WHERE   old."gebiedcode"     = tek."_gebiedcode"
                          AND     old."tekeningnummer" = tek."_tekeningnummer"
                          AND     old."fase"           = tek."_fase"
      					AND     old."revisie"        = tek."_revisie"
      				   )
      ;,FIRST,BestaandAfgesloten,SELECT old."revisie"
      ,      old."projectnaam"
      ,      old."tekeningnummer"
      ,      old."coordinator"
      ,      old."ontwerper"
      ,      old."tekenaar"
      ,      old."fase"
      ,      old."bestandsactualisatie"
      ,      old."vervaldatum"
      ,      old."identificatie"
      ,      old."ind_bordenplan"
      ,      old."ind_lichtplan"
      ,      old."reactiedoc"
      ,      old."datumUitzending"
      ,      old."tekeningfolder"
      ,      old."tekeningPDF"
      ,      old."opmerking"
      ,      old."gebiedcode"
      ,      old."gebiednaam"
      ,      0  AS actueel
      ,      new."ind_klaar"
      FROM   IP_overzicht      AS old
      ,      Uitzendingenlijst AS new
      WHERE  old."tekeningnummer" = new."IPnummer"
      AND    old."gebiedcode" = new."gebiedcode"
      AND    new."ind_klaar" = 1
      AND    old."ind_klaar" = 0
      ;,FIRST
    TABLE_DEF = Uitzendingenlijst,gebiedcode,varchar(3),IPnummer,varchar(200),fase,integer,locatie,varchar(200),ontwerper,varchar(200),tekenaar,varchar(200),coordinator,varchar(200),datumUitzending,varchar(200),ind_klaar,integer,vervaldatum,varchar(200),Tekeningenlijst,_gebiedcode,varchar(3),_tekeningnummer,varchar(200),_fase,integer,_revisie,integer,_tekeningpad,varchar(500),_tekeningfolder,varchar(500),_tekeningPDF,varchar(500),_reactiedoc,varchar(500),_ind_bordenplan,integer,_ind_lichtplan,integer,IP_overzicht,identificatie,text,gebiedcode,varchar(3),gebiednaam,varchar(500),projectnaam,varchar(100),tekeningnummer,varchar(50),fase,integer,revisie,integer,ontwerper,varchar(100),tekenaar,varchar(100),actueel,integer,ind_klaar,integer,datumUitzending,text,vervaldatum,text,coordinator,varchar(100),bestandsactualisatie,text,tekeningfolder,varchar(500),tekeningPDF,varchar(500),reactiedoc,varchar(500),ind_lichtplan,integer,ind_bordenplan,integer,opmerking,varchar(500)
    QUERY_SCHEMA = NieuwTekFase,gebiedcode,varchar(3),tekeningnummer,varchar(200),fase,integer,datumUitzending,varchar(200),vervaldatum,varchar(200),projectnaam,varchar(200),coordinator,varchar(200),ontwerper,varchar(200),tekenaar,varchar(200),ind_klaar,integer,NieuweRevisie,_tekeningpad,varchar(500),_tekeningfolder,varchar(500),_tekeningPDF,varchar(500),_reactiedoc,varchar(500),_ind_bordenplan,integer,_ind_lichtplan,integer,revisie,integer,gebiedcode,varchar(3),tekeningnummer,varchar(200),fase,integer,datumUitzending,varchar(200),vervaldatum,varchar(200),projectnaam,varchar(200),coordinator,varchar(200),ontwerper,varchar(200),tekenaar,varchar(200),ind_klaar,integer,BestaandAfgesloten,revisie,integer,projectnaam,varchar(100),tekeningnummer,varchar(50),coordinator,varchar(100),ontwerper,varchar(100),tekenaar,varchar(100),fase,integer,bestandsactualisatie,text,vervaldatum,text,identificatie,text,ind_bordenplan,integer,ind_lichtplan,integer,reactiedoc,varchar(500),datumUitzending,text,tekeningfolder,varchar(500),tekeningPDF,varchar(500),opmerking,varchar(500),gebiedcode,varchar(3),gebiednaam,varchar(500),actueel,,ind_klaar,integer
    NieuwTekFase -> InlineQuerierPotentieelGewijzigd [NieuwTekFase]
    NieuwTekFase -> FeatureMerger_UitzendingMetTekening [SUPPLIER]
    NieuweRevisie -> InlineQuerierPotentieelGewijzigd [NieuweRevisie]
    NieuweRevisie -> FeatureReader [INITIATOR]
    BestaandAfgesloten -> FeatureMerger [REQUESTOR]
Note: bestaande features waarbij een nieuwe / fase en/of revisie is geintroduceerd, / en die niet tegelijkertijd zijn afgesloten / (die worden apart behandeld via de poort / 'BestaandAfgesloten' in de transfomer / 'InlineQuerierTekening'. / Deze moeten worden bijgewerkt.
InlineQuerierPotentieelGewijzigd
    QUERY_DEF:
      potGewijzigd,SELECT old."revisie"
      ,      old."projectnaam"
      ,      old."tekeningnummer"
      ,      old."coordinator"
      ,      old."ontwerper"
      ,      old."tekenaar"
      ,      old."fase"
      ,      old."actueel"
      ,      old."bestandsactualisatie"
      ,      old."identificatie"
      ,      old."datumUitzending"
      ,      old."tekeningfolder"
      ,      old."tekeningPDF"
      ,      old."opmerking"
      ,      old."gebiedcode"
      ,      old."gebiednaam"
      ,      old."ind_bordenplan"
      ,      old."ind_klaar"
      ,      old."ind_lichtplan"
      ,      old."reactiedoc"
      ,      old."vervaldatum"
      FROM   "IP_Overzicht" AS old
      WHERE EXISTS (SELECT 'x'
                    FROM  "NieuweRevisie" AS nre
                    WHERE nre."gebiedcode" = old."gebiedcode"
                    AND   nre."tekeningnummer" = old."tekeningnummer"
                    AND   nre."ind_klaar" = old."ind_klaar"
                    )
      OR    EXISTS (SELECT 'x'
                    FROM  "NieuwTekFase" AS nte
                    WHERE nte."gebiedcode" = old."gebiedcode"
                    AND   nte."tekeningnummer" = old."tekeningnummer"
                    AND   nte."ind_klaar" = old."ind_klaar"
                    )
       ;,FIRST
    TABLE_DEF = NieuwTekFase,gebiedcode,varchar(3),tekeningnummer,varchar(50),fase,integer,datumUitzending,text,projectnaam,varchar(500),coordinator,varchar(200),ontwerper,varchar(200),tekenaar,varchar(200),ind_klaar,integer,vervaldatum,varchar(200),NieuweRevisie,_tekeningpad,varchar(500),_tekeningfolder,varchar(500),_tekeningPDF,varchar(500),_reactiedoc,varchar(500),_ind_bordenplan,integer,ind_lichtplan,integer,revisie,integer,gebiedcode,varchar(3),tekeningnummer,varchar(200),fase,integer,datumUitzending,text,projectnaam,varchar(200),coordinator,varchar(200),ontwerper,varchar(200),tekenaar,varchar(200),ind_klaar,integer,vervaldatum,text,IP_overzicht,OBJECTID,integer,identificatie,text,gebiedcode,varchar(3),gebiednaam,varchar(500),projectnaam,varchar(100),tekeningnummer,varchar(50),fase,integer,revisie,integer,ontwerper,varchar(100),tekenaar,varchar(100),actueel,integer,ind_klaar,integer,datumUitzending,text,vervaldatum,text,coordinator,varchar(100),bestandsactualisatie,text,tekeningfolder,varchar(500),tekeningPDF,varchar(500),reactiedoc,varchar(500),ind_lichtplan,integer,ind_bordenplan,integer,opmerking,varchar(500),SHAPE_Length,float,SHAPE_Area,float
    QUERY_SCHEMA = potGewijzigd,revisie,integer,projectnaam,varchar(100),tekeningnummer,varchar(50),coordinator,varchar(100),ontwerper,varchar(100),tekenaar,varchar(100),fase,integer,actueel,integer,bestandsactualisatie,text,identificatie,text,datumUitzending,text,tekeningfolder,varchar(500),tekeningPDF,varchar(500),opmerking,varchar(500),gebiedcode,varchar(3),gebiednaam,varchar(500),ind_bordenplan,integer,ind_klaar,integer,ind_lichtplan,integer,reactiedoc,varchar(500),vervaldatum,text
    potGewijzigd -> AttributeRenamer
Note: 'actueel' hernoemen naar '_old_actueel'. / Dit kenmerk wordt hierna opnieuw berekend. / Als verderop blijkt dat dit kenmerk gewijzigd is / moet een UPDATE volgen. In elk / ander geval moet deze feature worden genegeerd. / Dit kan worden uitgebreid naar andere kenmerken / waarvoor op een wijzigiing moet worden getoetst.
AttributeRenamer
    ATTR_TABLE = RENAME_SET_DEFAULT actueel > _old_actueel
    -> Actualiteitsbepaler [In]

Bookmark: koppelen uitzendingen aan tekeningen en vormen van contouren
  Plancontourenworden gevormd aan de hand van aangeleverde plangrenzen:
  clippen binnen gemeentegrens
  stroken van arcs 
  snappen van edges en vertices binnen 5 meter 
  vormen van polygioen uit lines, arcs en ellipses 
  verwijderen binnengrenzen 
  verwijderen polygonen zonder oppervlakte 
  aggregeren naar oorspronkelijk bestandsnaam + -pad 
  ophalen projectmetadata + bepalen van uitval
Note: zoeken van tekening / bij nieuw tekeningnummer / of nieuwe fase bij een / bestaand tekeningnummer.
FeatureMerger_UitzendingMetTekening
    SUPPLIERS_FIRST = No
    JOIN_KEYS = @Value(_gebiedcode) @Value(gebiedcode) AUTO @Value(_tekeningnummer) @Value(tekeningnummer) AUTO @Value(_fase) @Value(fase) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> AttributeRemover
    UNUSED_SUPPLIER -> AttributeCreator_uitzendingZonderTekening
    <REJECTED> -> Junction_16
AttributeRemover
    REMOVE_ATTRS = _fase,_revisie,_tekeningnummer,_gebiedcode
    -> FeatureReader [INITIATOR]
Note: inlezen autocadbestand bij / - nieuwe tekeningnummers / - bestaand tekeningnummer met nieuwe fase / - bestaand tekeningnummer + fase, met nieuwe revisie
FeatureReader
    ACAD_READ_USER_DICTIONARIES = no
    OUTPUT_FEATURES_DISPLAY = Data Features
    ACAD_READ_SYS_VARS = no
    ACAD_OUTPUT_ZERO_LENGTH_LINES_AS_LINES = no
    FEATURETYPES = X-XX-AL-PROJECTGRENS-G X-XX-AL-WIJZIGINGSGRENS-G  X-XX-AL-PROJECTGRENS_IP-G
    ACAD_PRESERVE_COMPLEX_HATCHES = no
    ACAD_RESOLVE_DIMENSIONS = yes
    ACAD_PRESERVE_CLIPPED_RASTERS = no
    ACAD_IGNORE_UCS = no
    ATTR_ACCUM_MODE = Only Use Result
    ACAD_RESOLVE_BLOCKS = yes
    ACAD_IGNORE_FROZEN_LAYERS = no
    ACAD_ALL_MERGED_FILTERS_NEED_NO_DEFS = Yes
    ACAD_READ_MODEL_SPACE = yes
    ACAD_METAFILE = acad
    FORMAT = ACAD
    ACAD_USE_BLOCK_HEADER_LAYER = yes
    ACAD_XRECORD_READING = None
    DATASET = @Value(_tekeningpad)
    ACAD_READ_PROXY_GRAPHICS = yes
    ACAD_USE_BLOCK_LAYER_INFO = no
    ACAD_USE_SEARCH_ENVELOPE = NO
    ACAD_STORE_BULGE_INFO = no
    ACAD_STORE_LAYER_INFO = no
    ACAD_READ_GROUPS = no
    ACAD_LIST_ATTRIBUTE_ENTITY_DATA = yes
    ACAD_APPLY_WORLD_FILE = yes
    ACAD_READ_PAPER_SPACE = NO
    ACAD_READ_AS_2_5D = no
    ACAD_QUERY_FEATURE_TYPES_FOR_MERGE_FILTERS = Yes
    ACAD_STORE_INSERT_POINT = no
    ACAD_RESOLVE_ENTITY_COLOR = yes
    ATTRS_TO_EXPOSE = autocad_source_filename
    ACAD_VISIBLE_ATTRIBUTES_AS_TEXT = yes
    ACAD_PRESERVE_INSERTS = no
    INTERACT = <No Spatial Filter>
    ACAD_EVALUATE_MLINE_GEOM = no
    ACAD_LIST_EXTENDED_DATA = yes
    COMBINE_GEOM = Use Result
    ACAD_CONVERT_ZERO_LENGTH_ARCS_TO_POINTS = yes
    ACAD_EXPLODE_MTEXT = yes
    COORDSYS = EPSG:28992
    ACAD_STRUCTURE_EXTENDED_DATA = no
    ACAD_STORE_SPLINE_DEFS = yes
    ACAD_READ_XREFS = no
    ACAD_INTERPRET_EXTENDED_DATA = yes
    <OTHER> -> ContourReconstructor [AutoCadFeatures]
    INITIATOR -> ContourReconstructor [Initiator]
    <REJECTED> -> AttributeCreator_uitzendingZonderTekening
AttributeCreator_uitzendingZonderTekening
    ATTR_TABLE = SET_TO _opmerking = Bij deze uitzending is geen tekening gevonden.
    -> AttributeManager_NieuwContour
Junction_16
    -> Junction_17
Note: TIR
Gemeente_vlakken (reader ESRISHAPE_1)
    attributes: GROEP char(9), KLASSE char(30), DGDT_ID long, CODE long, HERKOMST char(20), STATUS char(25), NIVO long, INWIN char(10), GEMEENTE long, GEBIED long, BUURT long, SUBBUURT long, SBTDEEL long, BLOK long, TEKST char(80), GEBDNAAM char(254), BUURTNAAM char(254), LAAG char(20)
    -> ContourReconstructor [Gemeente]
ContourReconstructor
    FASE = @Value(fase)
    GEBIEDCODE = @Value(gebiedcode)
    REVISIE = @Value(revisie)
    TEKENINGNUMMER = @Value(tekeningnummer)
    AUTOCAD_SOURCE_FILENAME = @Value(autocad_source_filename)
    _TEKENINGPAD = @Value(_tekeningpad)
    Uit -> AttributeManager_NieuwContour
    GeenContour -> AttributeManager_NieuwContour
    _Rejected_ -> Junction_4
Junction_4
    -> Junction_7

Bookmark: voorbereiden metadata voor nieuwe features
  Er wordt hier rekening gehouden met verschillende datumnotaties.
AttributeManager_NieuwContour
    ATTR_TABLE:
      RENAME_SET_VALUE _opmerking > opmerking
      RENAME_SET_VALUE _tekeningpad > tekeningpad
      RENAME_SET_VALUE _tekeningfolder > tekeningfolder
      RENAME_SET_VALUE _tekeningPDF > tekeningPDF
      REMOVE _reader_error
      REMOVE _matched_records
      RENAME_SET_VALUE _reactiedoc > reactiedoc
      RENAME_SET_VALUE _ind_bordenplan > ind_bordenplan
      RENAME_SET_VALUE _ind_lichtplan > ind_lichtplan
    -> TestFilter
Note: gebiednaam
AttributeValueMapper_2
    VAL_ATTR = gebiednaam
    LUT = CE,Centrum,CH,Charlois,DE,Delfshaven,FE,Feijenoord,HH,Hoek van Holland,HO,Hoogvliet,HS,Hillegersberg-Schiebroek,IJS,IJsselmonde,YS,IJsselmonde,KC,Kralingen-Crooswijk,NO,Noord,OV,Overschie,PA,Prins Alexander-Nesselande,PE,Pernis,RO,Rozenburg
    DIRECTION = Forward (Source To Destination)
    SRC = gebiedcode
    -> Actualiteitsbepaler [In]
Terminator_3
    MESSAGE = vervaldatum heeft een afwijkend formaat
Junction_12
    -> Junction_14
Terminator
    MESSAGE = datumUItzending heeft een afwijkend formaat

Bookmark: formatteren datum uitzending
TestFilter
    DEFAULT_VALUE = <UNFILTERED>
    TEST_LIST = BOOL_OP,OR,COMPOSITE_TEST,<Unused>,TEST_CLAUSE,"TEST @Value(datumUitzending) CONTAINS_REGEX ^\d{8}$",^\d{8}$,BOOL_OP,OR,COMPOSITE_TEST,<Unused>,TEST_CLAUSE,"TEST @Value(datumUitzending) CONTAINS_REGEX ^\d-\d{1,2}-\d{4}$",^\d-\d{1,2}-\d{4}$,BOOL_OP,OR,COMPOSITE_TEST,<Unused>,TEST_CLAUSE,"TEST @Value(datumUitzending) CONTAINS_REGEX ^\d{2}-\d{1,2}-\d{4}$",^\d{2}-\d{1,2}-\d{4}$
    ^\d{8}$ -> DateTimeConverter_Ymd
    ^\d-\d{1,2}-\d{4}$ -> DateTimeConverter_eNY
    ^\d{2}-\d{1,2}-\d{4}$ -> DateTimeConverter_dNY
    <UNFILTERED> -> Terminator
DateTimeConverter_Ymd
    IN_FORMAT = %Y%m%d$
    OUT_FORMAT = FME
    REPAIR_INPUT = NO
    DATETIME_ATTR = datumUitzending
    -> DateTimeConverter_dNY_OUTPUT_-__AttributeValueMapper
    <REJECTED> -> Junction_22
DateTimeConverter_eNY
    IN_FORMAT = %e-%N-%Y
    OUT_FORMAT = FME
    REPAIR_INPUT = NO
    DATETIME_ATTR = datumUitzending
    -> DateTimeConverter_dNY_OUTPUT_-__AttributeValueMapper
    <REJECTED> -> Junction_22
DateTimeConverter_dNY
    IN_FORMAT = %d-%N-%Y
    OUT_FORMAT = FME
    REPAIR_INPUT = NO
    DATETIME_ATTR = datumUitzending
    -> DateTimeConverter_dNY_OUTPUT_-__AttributeValueMapper
    <REJECTED> -> Junction_22
DateTimeConverter_dNY_OUTPUT_-__AttributeValueMapper: Junction
    -> TestFilter_2
Junction_22
    -> Junction_12

Bookmark: formatteren vervaldatum
TestFilter_2
    DEFAULT_VALUE = <UNFILTERED>
    TEST_LIST = BOOL_OP,OR,COMPOSITE_TEST,<Unused>,TEST_CLAUSE,"TEST @Value(vervaldatum) NOT_ATTRIBUTE_HAS_VALUE """"",geenWaarde,BOOL_OP,OR,COMPOSITE_TEST,<Unused>,TEST_CLAUSE,"TEST @Value(vervaldatum) CONTAINS_REGEX ^\d{8}$",^\d{8}$,BOOL_OP,OR,COMPOSITE_TEST,<Unused>,TEST_CLAUSE,"TEST @Value(vervaldatum) CONTAINS_REGEX ^\d-\d{1,2}-\d{4}$",^\d-\d{1,2}-\d{4}$,BOOL_OP,OR,COMPOSITE_TEST,<Unused>,TEST_CLAUSE,"TEST @Value(vervaldatum) CONTAINS_REGEX ^\d{2}-\d{1,2}-\d{4}$",^\d{2}-\d{1,2}-\d{4}$
    geenWaarde -> DateTimeConverter_dNY_OUTPUT_-__AttributeValueMapper_2
    ^\d{8}$ -> DateTimeConverter_Ymd_2
    ^\d-\d{1,2}-\d{4}$ -> DateTimeConverter_eNY_2
    ^\d{2}-\d{1,2}-\d{4}$ -> DateTimeConverter_dNY_2
    <UNFILTERED> -> Terminator_3
DateTimeConverter_Ymd_2
    IN_FORMAT = %Y%m%d$
    OUT_FORMAT = FME
    REPAIR_INPUT = NO
    DATETIME_ATTR = vervaldatum
    -> DateTimeConverter_dNY_OUTPUT_-__AttributeValueMapper_2
    <REJECTED> -> Junction_9
DateTimeConverter_eNY_2
    IN_FORMAT = %e-%N-%Y
    OUT_FORMAT = FME
    REPAIR_INPUT = NO
    DATETIME_ATTR = vervaldatum
    -> DateTimeConverter_dNY_OUTPUT_-__AttributeValueMapper_2
    <REJECTED> -> Junction_9
DateTimeConverter_dNY_2
    IN_FORMAT = %d-%N-%Y
    OUT_FORMAT = FME
    REPAIR_INPUT = NO
    DATETIME_ATTR = vervaldatum
    -> DateTimeConverter_dNY_OUTPUT_-__AttributeValueMapper_2
    <REJECTED> -> Junction_9
DateTimeConverter_dNY_OUTPUT_-__AttributeValueMapper_2: Junction
    -> AttributeValueMapper_2
Junction_9
    -> Junction_12

Bookmark: voorbereiding database INSERT
Note: revisie op 1 zetten / als revisie niet bekend is
RevisieSetter_INS
    REVISIE = @Value(revisie)
    Uit -> GUIDGenerator_INS
Note: aanmaken uniek id
GUIDGenerator_INS
    -> AttributeRenamer_identficatie_INS
AttributeRenamer_identficatie_INS
    ATTR_TABLE = RENAME_SET_DEFAULT GFID > identificatie
    -> AttributeCreator_INS
Note: fme_db_operation := INSERT
AttributeCreator_INS
    ATTR_TABLE = SET_TO fme_db_operation = INSERT
    -> DateTimeStamper_2

Bookmark: voorbereiding database UPDATE
Note: ophalen oorspronkelijkgeometrie. / Deze komen niet mee in de InlineQueriers. / Een alternatief is om daar / expliciet SELECT fme_feature_content / toe te passen, / maar dan komen alle kenmerken mee.
FeatureMerger
    SUPPLIERS_FIRST = No
    JOIN_KEYS = @Value(identificatie) @Value(identificatie) AUTO
    MERGE_TYPE = Geometry
    REJECT_NULL_MISSING_KEYS = No
    PROCESS_DUPS = No
    MERGED -> FeatureMerger_MERGED_-__AttributeCreator_UPD
    UNMERGED_REQUESTOR -> FeatureMerger_MERGED_-__AttributeCreator_UPD
    <REJECTED> -> Junction_20
FeatureMerger_MERGED_-__AttributeCreator_UPD: Junction
    -> AttributeRemover_2
AttributeRemover_2
    REMOVE_ATTRS = bestandsactualisatie
    -> AttributeCreator_UPD
Note: fme_db_operation := UPDATE
AttributeCreator_UPD
    ATTR_TABLE = SET_TO fme_db_operation = UPDATE
    -> DateTimeStamper_2
Junction_20
    -> Junction_21

Bookmark: bepalen oppervlakte groen (was/wordt) tbv vergroeningsopgave
Note: Projectgrenzen van IP's die / nieuw aan het overzicht worden toegevoegd / en waarbij een contour kon worden gevormd.
AttributeKeeper_Groen
    KEEP_ATTRS = bestandsactualisatie,tekeningpad,identificatie,revisie,tekeningnummer,fase
    -> AttributeKeeper_2
    -> FeatureMerger_WasWordtMeta [SUPPLIER]
Note: Opnieuw inlezen van de autocad-tekeningen / bij de IP's om zo de groenvlakken te extraheren. / Dit gebeurt alleen voor nieuwe uitzendingen, / en alleen als er eerder in het script succesvol / een contour is bepaald.
AttributeKeeper_2
    KEEP_ATTRS = tekeningpad,identificatie
    -> FeatureReaderBGT [INITIATOR]
    -> FeatureReader_Groen_IP [INITIATOR]
FeatureMerger_WasWordt
    SUPPLIERS_FIRST = No
    JOIN_KEYS = @Value(identificatie) @Value(identificatie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_WasWordt_MERGED_-__FeatureMerger_WasWordt_Merged
    UNMERGED_REQUESTOR -> FeatureMerger_WasWordt_MERGED_-__FeatureMerger_WasWordt_Merged
    UNUSED_SUPPLIER -> FeatureMerger_WasWordt_MERGED_-__FeatureMerger_WasWordt_Merged
    <REJECTED> -> Junction_39
FeatureMerger_WasWordt_MERGED_-__FeatureMerger_WasWordt_Merged: Junction
    -> FeatureMerger_WasWordtMeta [REQUESTOR]
Note: ophalen oorspronkelijke / metadata van het IP
FeatureMerger_WasWordtMeta
    SUPPLIERS_FIRST = No
    JOIN_KEYS = @Value(identificatie) @Value(identificatie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> FeatureMerger_WasWordtMeta_MERGED
    UNMERGED_REQUESTOR -> FeatureMerger_WasWordtMeta_MERGED
    UNUSED_SUPPLIER -> FeatureMerger_WasWordtMeta_MERGED
    <REJECTED> -> Junction_41
FeatureMerger_WasWordtMeta_MERGED: Junction
    -> IP_Groen (writer CSV2_2)
Junction_41
    -> Junction_42
Junction_39
    -> Junction_40

Bookmark: Bepalen oppervlakte groen WAS
Note: inlezen BGT per projectgrens / Met deze featurereader wordt voorkomen dat / steeds de hele BGT wordt ingelezen. / Objecten worden alleen ingelezen als ze een / 'groen' fysiek voorkomen hebben en met de / projectgrens overlappen
FeatureReaderBGT
    GEODATABASE_FILE_SPLIT_COMPLEX_ANNOS = no
    FORMAT = GEODATABASE_FILE
    INTERACT = Intersects
    GEODATABASE_FILE_QUERY_FEATURE_TYPES_FOR_MERGE_FILTERS = Yes
    COMBINE_GEOM = Use Result
    GEODATABASE_FILE_TRANSLATE_SPATIAL_DATA_ONLY = no
    GEODATABASE_FILE_MERGE_FEAT_LINKED_ANNOS = no
    DATASET = $(P_BRON_GROEN_BGT)
    GEODATABASE_FILE_RESOLVE_SUBTYPE_NAMES = yes
    GEODATABASE_FILE_SPLIT_MULTI_PART_ANNOS = no
    GEODATABASE_FILE_FEATURE_READ_MODE = Features
    GEODATABASE_FILE_ALIAS_MODE = NONE
    OUTPUT_FEATURES_DISPLAY = Schema and Data Features
    GEODATABASE_FILE_IGNORE_RELATIONSHIP_INFO = yes
    GEODATABASE_FILE_USE_SEARCH_ENVELOPE = NO
    GEODATABASE_FILE_CHECK_SIMPLE_GEOM = no
    GEODATABASE_FILE_IGNORE_NETWORK_INFO = yes
    GEODATABASE_FILE_RESOLVE_DOMAINS = no
    ATTRS_TO_EXPOSE = FYSIEKVK
    COORDSYS = EPSG:28992
    GEODATABASE_FILE_SPLIT_COMPLEX_EDGES = no
    FEATURETYPES = BGT_Vlakken
    ATTR_ACCUM_MODE = Only Use Result
    GEODATABASE_FILE_CACHE_MULTIPATCH_TEXTURES = yes
    WHERE = $(P_BRON_GROEN_BGT_WHERE)
    <OTHER> -> Clipper_BGT_projectgrens [CLIPPEE]
    INITIATOR -> Clipper_BGT_projectgrens [CLIPPER]
    <REJECTED> -> Junction_31
Note: Clippen van de BGT-objecten / op de projectgrens.
Clipper_BGT_projectgrens
    BOUNDARY_CASES = Treat as Inside
    LINES_AS_SEGMENTS = No
    PRESERVE_CLIPPEE_EXTENTS = No
    VAL_SOURCE = Clippee Only
    MEASURE_TYPE = Continuous
    MISSING_VAL_MODE = Compute
    CREATE_AGGREGATES = Yes
    CLIP_TYPE = Multiple Clippers
    ATTR_ACCUM_MODE = Merge Clipper
    ATTR_CONFLICT_RES = Use Clippee
    INSIDE -> CoordinateRounder_Heel
    <REJECTED> -> Junction_33
CoordinateRounder_Heel
    XPREC = 3
    ZPREC = 0
    YPREC = 3
    ROUNDED -> Dissolver_Heel
Note: Samenvoegen van groenvlakken / uit de BGT. Alle groenvlakken / tellen 100% mee.
Dissolver_Heel
    GROUP_BY = identificatie
    CONNECT_Z_MODE = First Wins
    NO_OVRLP = No
    ACCUM_INPUT_ATTRS = Use Attributes From One Feature
    DEAGGREGATE_INPUT = Yes
    AREA -> AttributeManager_BGT
    <REJECTED> -> Junction_35
AttributeManager_BGT
    ATTR_TABLE:
      REMOVE tekeningpad
      REMOVE _matched_records
      REMOVE FYSIEKVK
      SET_TO _factor = 1
    -> OppervlaktetotaalBerekenaar_BGT [IN]
Note: Oppervlaktes groen berekenen / en per IP sommeren.
OppervlaktetotaalBerekenaar_BGT
    _FACTOR = @Value(_factor)
    IDENTIFICATIE = @Value(identificatie)
    Uit -> AttributeManager_Was
    <Rejected> -> Junction_37
AttributeManager_Was
    ATTR_TABLE = RENAME_SET_VALUE opp_m2 > opp_m2_was
    -> FeatureMerger_WasWordt [REQUESTOR]
Junction_37
    -> Junction_38
Junction_35
    -> Junction_36
Junction_33
    -> Junction_34
Junction_31
    -> Junction_32

Bookmark: uitval vergroeningsgegevens
Junction_38
    -> _Rejected_Groen_
Junction_36
    -> _Rejected_Groen_
Junction_34
    -> _Rejected_Groen_
Junction_32
    -> _Rejected_Groen_
Junction_44
    -> _Rejected_Groen_
Junction_42
    -> _Rejected_Groen_
Junction_40
    -> _Rejected_Groen_
Junction_30
    -> _Rejected_Groen_
Junction_46
    -> _Rejected_Groen_
Junction_26
    -> _Rejected_Groen_
Junction_24
    -> _Rejected_Groen_
_Rejected_Groen_: Logger
    MAXFEATS = 20
    MESSAGE = Feature is:
    MAXCOORDS = 20

Bookmark: Bepalen oppervlakte groen WORDT
FeatureReader_Groen_IP
    ACAD_READ_USER_DICTIONARIES = no
    OUTPUT_FEATURES_DISPLAY = Data Features
    ACAD_READ_SYS_VARS = no
    ACAD_OUTPUT_ZERO_LENGTH_LINES_AS_LINES = no
    ATTR_CONFLICT_RES = Use Result
    ACAD_PRESERVE_COMPLEX_HATCHES = no
    ACAD_RESOLVE_DIMENSIONS = yes
    ACAD_PRESERVE_CLIPPED_RASTERS = no
    ACAD_IGNORE_UCS = no
    ATTR_ACCUM_MODE = Merge Initiator and Result
    ACAD_RESOLVE_BLOCKS = yes
    ACAD_IGNORE_FROZEN_LAYERS = no
    ACAD_ALL_MERGED_FILTERS_NEED_NO_DEFS = Yes
    ACAD_READ_MODEL_SPACE = yes
    ACAD_METAFILE = acad
    FORMAT = ACAD
    ACAD_USE_BLOCK_HEADER_LAYER = yes
    ACAD_XRECORD_READING = None
    DATASET = @Value(tekeningpad)
    ACAD_READ_PROXY_GRAPHICS = yes
    ACAD_USE_BLOCK_LAYER_INFO = no
    ACAD_USE_SEARCH_ENVELOPE = NO
    ACAD_STORE_BULGE_INFO = no
    ACAD_STORE_LAYER_INFO = no
    ACAD_READ_GROUPS = no
    ACAD_LIST_ATTRIBUTE_ENTITY_DATA = yes
    ACAD_APPLY_WORLD_FILE = yes
    ACAD_READ_PAPER_SPACE = NO
    ACAD_READ_AS_2_5D = no
    ACAD_STORE_INSERT_POINT = no
    ACAD_QUERY_FEATURE_TYPES_FOR_MERGE_FILTERS = Yes
    ACAD_RESOLVE_ENTITY_COLOR = yes
    ATTRS_TO_EXPOSE = fme_feature_type
    ACAD_VISIBLE_ATTRIBUTES_AS_TEXT = yes
    ACAD_PRESERVE_INSERTS = no
    INTERACT = <No Spatial Filter>
    ACAD_LIST_EXTENDED_DATA = yes
    ACAD_EVALUATE_MLINE_GEOM = no
    COMBINE_GEOM = Use Result
    ACAD_CONVERT_ZERO_LENGTH_ARCS_TO_POINTS = yes
    ACAD_EXPLODE_MTEXT = yes
    COORDSYS = EPSG:28992
    ACAD_STRUCTURE_EXTENDED_DATA = no
    ACAD_STORE_SPLINE_DEFS = yes
    ACAD_READ_XREFS = no
    ACAD_INTERPRET_EXTENDED_DATA = yes
    <OTHER> -> TestFilter_IP_Groen
    INITIATOR -> Clipper_Groen_IP_projectgrens [CLIPPER]
    <REJECTED> -> Junction_23
TestFilter_IP_Groen
    DEFAULT_VALUE = <UNFILTERED>
    TEST_LIST:
      BOOL_OP,OR,COMPOSITE_TEST,<Unused>,TEST_CLAUSE,"TEST @Value(fme_feature_type) CONTAINS_REGEX -S$",Symbool,BOOL_OP,AND,COMPOSITE_TEST,<Unused>,TEST_CLAUSE,"TEST @Value(fme_feature_type) CONTAINS_REGEX ^[B|N]-PV-GR-
      TEST @Value(fme_feature_type) NOT_CONTAINS_REGEX -BOOM",Groen_nietBoom,BOOL_OP,OR,COMPOSITE_TEST,<Unused>,TEST_CLAUSE,"TEST @Value(fme_feature_type) CONTAINS_REGEX ^[B|N]-PV-.*BESCHOEIING",Beschoeiing,BOOL_OP,OR,COMPOSITE_TEST,<Unused>,TEST_CLAUSE,"TEST @Value(fme_feature_type) CONTAINS_REGEX ^[B|N]-PV-.*NATUUROEVER",Natuuroever,BOOL_OP,OR,COMPOSITE_TEST,<Unused>,TEST_CLAUSE,"TEST @Value(fme_feature_type) CONTAINS_REGEX ^[B|N]-PV-.*PLASBERM",Plasberm,BOOL_OP,OR,COMPOSITE_TEST,<Unused>,TEST_CLAUSE,"TEST @Value(fme_feature_type) CONTAINS_REGEX ^[B|N]-PV-.*WADI",Wadi,BOOL_OP,OR,COMPOSITE_TEST,<Unused>,TEST_CLAUSE,"TEST @Value(fme_feature_type) CONTAINS_REGEX ^[B|N]-PV-.*GRASBETONSTEEN",Grasbetonsteen,BOOL_OP,OR,COMPOSITE_TEST,<Unused>,TEST_CLAUSE,"TEST @Value(fme_feature_type) CONTAINS_REGEX ^[B|N]-PV-.*HALFVERHARDING",Halfverharding,BOOL_OP,OR,COMPOSITE_TEST,<Unused>,TEST_CLAUSE,"TEST @Value(fme_feature_type) CONTAINS_REGEX ^[B|N]-PV-.*TEGEL_GRAS",Tegel_gras
    Groen_nietBoom -> AttributeCreator_factorHeel
    Beschoeiing -> AttributeCreator_factorHeel
    Natuuroever -> AttributeCreator_factorHeel
    Plasberm -> AttributeCreator_factorHeel
    Wadi -> AttributeCreator_factorHeel
    Grasbetonsteen -> AttributeCreator_factorHalf
    Halfverharding -> AttributeCreator_factorHalf
    Tegel_gras -> AttributeCreator_factorHalf
GeometryFilter_Groen_Area
    BREAK_AGG = No
    GEOM_PORT_NAMES = Area Ellipse
    AREA -> ArcStroker_IP_Groen
    ELLIPSE -> ArcStroker_IP_Groen
ArcStroker_IP_Groen
    STROKE_CHOICE = Number of Interpolated Edges
    NUM = 0
    MAKE_POLY = No
    STROKED -> Clipper_Groen_IP_projectgrens [CLIPPEE]
    <REJECTED> -> Junction_43
Junction_43
    -> Junction_44
Clipper_Groen_IP_projectgrens
    GROUP_BY = identificatie
    BOUNDARY_CASES = Treat as Inside
    LINES_AS_SEGMENTS = No
    PRESERVE_CLIPPEE_EXTENTS = No
    VAL_SOURCE = Clippee Only
    MEASURE_TYPE = Continuous
    MISSING_VAL_MODE = Compute
    CREATE_AGGREGATES = Yes
    CLIP_TYPE = Multiple Clippers
    ATTR_ACCUM_MODE = Merge Clipper
    ATTR_CONFLICT_RES = Use Clippee
    INSIDE -> AttributeFilter_IP_Groen_factor
    <REJECTED> -> Junction_25
AttributeFilter_IP_Groen_factor
    ATTR_VALUES = <Empty>,<Missing>,<Null>,<Unfiltered>,1,0.5
    ATTR_NAME = _factor
    1 -> VlakDissolverEnClipper_IP [Heel]
    0.5 -> VlakDissolverEnClipper_IP [Half]
Note: Groenvlakken per IP / samenvoegen. / Als heel groen overlapt met / half groen, dan gaat daar half / groen voor.
VlakDissolverEnClipper_IP
    GROUP_BY = identificatie
    IDENTIFICATIE = @Value(identificatie)
    Uit -> AttributeKeeper_IP_groen
    <Rejected> -> Junction_45
AttributeKeeper_IP_groen
    KEEP_ATTRS = identificatie,_factor
    -> OppervlaktetotaalBerekenaar_IP [IN]
Note: Oppervlaktes heel en half / groen berekenen en per IP / sommeren.
OppervlaktetotaalBerekenaar_IP
    _FACTOR = @Value(_factor)
    IDENTIFICATIE = @Value(identificatie)
    Uit -> AttributeManager_Wordt
    <Rejected> -> Junction_29
AttributeManager_Wordt
    ATTR_TABLE = RENAME_SET_VALUE opp_m2 > opp_m2_wordt
    -> FeatureMerger_WasWordt [SUPPLIER]
Junction_29
    -> Junction_30
Junction_45
    -> Junction_46
Junction_25
    -> Junction_26
Junction_23
    -> Junction_24

Bookmark: toekennen kenmerk '_factor'
AttributeCreator_factorHeel
    ATTR_TABLE = SET_TO _factor = 1
    -> AttributeCreator_factorHeel_OUTPUT_-__GeometryFilter_Groen_Area
AttributeCreator_factorHalf
    ATTR_TABLE = SET_TO _factor = 0.5
    -> AttributeCreator_factorHeel_OUTPUT_-__GeometryFilter_Groen_Area
AttributeCreator_factorHeel_OUTPUT_-__GeometryFilter_Groen_Area: Junction
    -> GeometryFilter_Groen_Area

Bookmark: wegschrijven gegevens over groen
IP_Groen (writer CSV2_2)
    attributes: identificatie string, tekeningnummer string, fase int8, revisie int8, opp_m2_was int64, opp_m2_wordt int64, bestandsactualisatie string

Bookmark: wegschrijven mutaties en uitval
IP_overzicht (writer GEODATABASE_FILE_3)
    attributes: identificatie guid, gebiedcode char(3), gebiednaam char(500), projectnaam char(100), tekeningnummer char(50), fase smallint, revisie smallint, ontwerper char(100), tekenaar char(100), actueel smallint, ind_klaar smallint, datumUitzending date, vervaldatum date, coordinator char(100), bestandsactualisatie date, tekeningfolder char(500), tekeningPDF char(500), reactiedoc char(500), ind_lichtplan smallint, ind_bordenplan smallint, opmerking char(500)
uitzending_zonder_tekening (writer CSV2_3)
    attributes: identificatie string, gebiedcode string, gebiednaam string, projectnaam string, tekeningnummer string, fase string, revisie string, datumUitzending string, coordinator string, ontwerper string, tekenaar string, tekeningfolder string, bestandsactualisatie string, opmerking string
uitzending_zonder_contour (writer CSV2_3)
    attributes: identificatie string, gebiedcode string, gebiednaam string, projectnaam string, tekeningnummer string, fase string, revisie string, datumUitzending string, coordinator string, ontwerper string, tekenaar string, tekeningfolder string, bestandsactualisatie string, opmerking string

FME custom transformer ContourReconstructor
Maakt plancontouren aan aan de hand van aangeleverde plangrenzen.
    clippen op gemeentegrens
    stroken van arcs 
    snappen van edges en vertices binnen 5 meter 
    vormen van polyginen uit lines, arcs en ellipses 
    verwijderen binnengrenzen 
    verwijderen polygonen zonder oppervlakte 
    aggregeren naar oorspronkelijk bestandsnaam + -pad 
    ophalen projectmetadata + bepalen van uitval

Parameters:
- AUTOCAD_SOURCE_FILENAME = @Value(autocad_source_filename)   # Autocad Source Filename
- _TEKENINGPAD = @Value(_tekeningpad)   # Tekeningpad
- FASE = @Value(fase)   # fase
- GEBIEDCODE = @Value(gebiedcode)   # gebiedcode
- REVISIE = @Value(revisie)   # revisie
- TEKENINGNUMMER = @Value(tekeningnummer)   # tekeningnummer

AutoCadFeatures (input)
    -> AttributeKeeper
AttributeKeeper
    KEEP_ATTRS = autocad_source_filename
    -> Clipper [CLIPPEE]
Gemeente (input)
    -> Clipper [CLIPPER]
Note: clippen op gemeentegrens
Clipper
    BOUNDARY_CASES = Treat as Inside
    LINES_AS_SEGMENTS = No
    CLIPPED_ATTR = _clipped
    PRESERVE_CLIPPEE_EXTENTS = No
    VAL_SOURCE = Clippee Only
    MEASURE_TYPE = Continuous
    MISSING_VAL_MODE = Compute
    CREATE_AGGREGATES = Yes
    CLIP_TYPE = Single Clipper
    INSIDE -> GeometryFilter_2
    <REJECTED> -> Junction_11
Initiator (input)
    -> AttributeRemover
AttributeRemover
    REMOVE_ATTRS = autocad_source_filename
    -> DuplicateFilter
DuplicateFilter
    KEYATTR = _tekeningpad
    INPUT_ORDERED_CHOICE = No
    UNIQUE -> FeatureMerger [REQUESTOR]
Note: Bepalen van tekeningen zonder / gereconstrueerde contour / en ophalen projectmetadata. / Match op basis van oorspronkeliijke / bestandsnaam + folder van de / autocad-tekening.
FeatureMerger
    SUPPLIERS_FIRST = No
    JOIN_KEYS = @Value(_tekeningpad) @Value(autocad_source_filename) AUTO
    MERGE_TYPE = Geometry
    REJECT_NULL_MISSING_KEYS = No
    PROCESS_DUPS = No
    MERGED -> AttributeManager_2
    UNMERGED_REQUESTOR -> AttributeCreator_geenContour
    <REJECTED> -> Junction_3
AttributeManager_2
    -> Uit (output)
Uit (output)
AttributeCreator_geenContour
    ATTR_TABLE = SET_TO _opmerking = Bij deze uitzending kon geen contour worden gevormd.
    -> AttributeManager_3
AttributeManager_3
    ATTR_TABLE = RENAME_SET_VALUE _opmerking > opmerking
    -> GeenContour (output)
GeenContour (output)
Junction_3
    -> Junction_4

Bookmark: waar nodig vormen van polygonen en aggregeren naaroorspronkelijke bestandsnaam
GeometryFilter_2
    BREAK_AGG = No
    GEOM_PORT_NAMES = Line Arc Area Ellipse
    LINE -> ArcStroker
    ARC -> ArcStroker
    AREA -> ArcStroker
    ELLIPSE -> ArcStroker
ArcStroker
    STROKE_CHOICE = Number of Interpolated Edges
    NUM = 0
    MAKE_POLY = No
    STROKED -> GeometryFilter
    <REJECTED> -> Junction
GeometryFilter
    BREAK_AGG = No
    GEOM_PORT_NAMES = Line Arc Area Ellipse
    LINE -> AreaBuilder
    ARC -> AreaBuilder
    AREA -> Dissolver
    ELLIPSE -> AreaBuilder
Note: per oosrspronkelijke autocadtekening
AreaBuilder
    DONUT_CREATION = NO
    GROUP_BY = autocad_source_filename
    POLY_ACCUM_ATTRS_NAME = Use Attributes From One Feature
    SNAP_TOLERANCE = 5
    LINES_AS_SEGMENTS = No
    CONNECT_Z_MODE = First Wins
    SNAPTYPE_PARAM = Vertex Snapping
    CHECK_CURVE_DIRECTION = No
    CONSIDER_NODE_ELEVATION = no
    ALLOW_CYCLES = No
    AREA -> Dissolver
    <REJECTED> -> Junction_9
Note: per oosrspronkelijke autocadtekening
Dissolver
    GROUP_BY = autocad_source_filename
    CONNECT_Z_MODE = First Wins
    NO_OVRLP = No
    ACCUM_INPUT_ATTRS = Use Attributes From One Feature
    DEAGGREGATE_INPUT = Yes
    AREA -> AreaCalculator
    <REJECTED> -> Junction_7
Note: oppervlakte > 0?
AreaCalculator
    AREA_TYPE = Plane Area
    AREA_ATTR = _area
    MULT = 1
    -> Tester_oppervlakte
    <REJECTED> -> Junction_5
Tester_oppervlakte
    TEST_MODE = Automatic
    TEST_DESCRIPTION = ""
    BOOL_OP = OR
    TEST_CLAUSE = TEST @Value(_area) > 0
    PASSED -> Aggregator
Note: per oosrspronkelijke autocadtekening
Aggregator
    GROUP_BY = autocad_source_filename
    MODE = Geometry - Assemble One Level
    SEP = ,
    AGGREGATE_TYPE = Homogeneous Collection (If Possible)
    ACCUM_ATTRS_NAME = Use Attributes From One Feature
    ORDERED = No
    AGGREGATE -> FeatureMerger [SUPPLIER]
Junction_5
    -> Junction_6
Junction_7
    -> Junction_8
Junction_9
    -> Junction_10
Junction
    -> Junction_2
Junction_11
    -> Junction_12

Bookmark: _rejected_
Junction_6
    -> _Rejected_ (output)
Junction_8
    -> _Rejected_ (output)
Junction_10
    -> _Rejected_ (output)
Junction_2
    -> _Rejected_ (output)
Junction_12
    -> _Rejected_ (output)
Junction_4
    -> _Rejected_ (output)
_Rejected_ (output)

FME custom transformer FaseRemapper
Converteert de fase van integer naar een omschrijving:
1 -->  concept
2 --> VUZ (voorlopige uitzending)
3 -->  LVUZ (laatste voorlopige uitzending)
4 --> GUZ (goedkeuringsuitzending)
5 --> DUZ (definitieve uitzending)
6 --> WUZ (wijzigingsuitzending)

Parameters:
- FASE = @Value(fase)   # fase

IN (input)
    -> AttributeValueMapper_Fase_int_naar_char
AttributeValueMapper_Fase_int_naar_char
    VAL_ATTR = fase
    LUT = 1,PVE,2,VUZ,3,LVUZ,4,GUZ,5,DUZ,6,WUZ
    DIRECTION = Forward (Source To Destination)
    SRC = fase
    -> UIT (output)
UIT (output)

FME custom transformer RevisieSetter
Het kenmerk 'revisie' wordt op 1 gezet als het leeg is.

Parameters:
- REVISIE = @Value(revisie)   # revisie

In (input)
    -> Tester_revisie_hasValue
Uit (output)

Bookmark: revisie op 1 zetten als revisie geen waarde heeft
Tester_revisie_hasValue
    TEST_MODE = Automatic
    TEST_DESCRIPTION = ""
    BOOL_OP = OR
    TEST_CLAUSE = TEST @Value(revisie) ATTRIBUTE_HAS_VALUE ""
    PASSED -> AttributeCreator_Revisie1_OUTPUT_-__SMP_overzicht
    FAILED -> AttributeCreator_Revisie1
AttributeCreator_Revisie1
    ATTR_TABLE = SET_TO revisie = 1
    -> AttributeCreator_Revisie1_OUTPUT_-__SMP_overzicht
AttributeCreator_Revisie1_OUTPUT_-__SMP_overzicht: Junction
    -> Uit (output)

FME custom transformer Actualiteitsbepaler

Parameters:
- REVISIE = @Value(revisie)   # revisie
- FASE = @Value(fase)   # fase
- TEKENINGNUMMER = @Value(tekeningnummer)   # tekeningnummer
- IND_KLAAR = @Value(ind_klaar)   # Ind Klaar

In (input)
    -> Tester_klaar
Note: Is de uitzending afgerond? / zo ja: actueel := 0
Tester_klaar
    TEST_MODE = Automatic
    TEST_DESCRIPTION = ""
    BOOL_OP = OR
    TEST_CLAUSE = TEST @Value(ind_klaar) = 1
    PASSED -> AttributeCreator_actueel_klaar
    FAILED -> AttributeKeeper
    FAILED -> FeatureMerger_3 [REQUESTOR]
AttributeCreator_actueel_klaar
    ATTR_TABLE = SET_TO actueel = 0
    -> Uit (output)
Note: Attributes to Keep: / revisie,fase,tekeningnummer
AttributeKeeper
    KEEP_ATTRS = revisie,fase,tekeningnummer
    -> AttributeCopier
Note: per tekeningnummer / een lijst maken met / fase en revisie
ListBuilder
    LIST_ATTRS_TO_INCLUDE = fase revisie _faserevisie
    GROUP_BY = tekeningnummer
    GROUPS_ORDERED = No
    LIST_NAME = _list
    -> ListElementCounter
ListElementCounter
    CNT_ATTR = _element_count
    LIST_NAME = _list{}
    -> Tester_3
Note: als er maar 1 combi / fase/revisie is dan is / die tekening per definitie / actueel
Tester_3
    TEST_MODE = Automatic
    TEST_DESCRIPTION = ""
    BOOL_OP = OR
    TEST_CLAUSE = TEST @Value(_element_count) <= 1
    PASSED -> ListExploder
    FAILED -> ListSorter
Note: sorteren op fase+revisie; / de hoogste waarde / (de actuele versie) komt / heeft index 0.
ListSorter
    SRC_LIST = _list{}._faserevisie
    TYPE = Alphabetic
    ORDER = Descending
    -> ListExploder
ListExploder
    ATTR_CONFLICT_RES = Use List Attribute Values
    ATTR_ACCUM_MODE = Merge List Attributes
    LIST_ATTR = _list{}
    INDEX_ATTR = _element_index
    ELEMENTS -> Tester_4
    <REJECTED> -> <Rejected> (output)
Note: list index = 0?
Tester_4
    TEST_MODE = Automatic
    TEST_DESCRIPTION = ""
    BOOL_OP = OR
    TEST_CLAUSE = TEST @Value(_element_index) = 0
    PASSED -> AttributeCreator_actueel_1
    FAILED -> AttributeCreator_actueel_0
AttributeCreator_actueel_1
    ATTR_TABLE = SET_TO actueel = 1
    -> AttributeKeeper_2
AttributeCreator_actueel_0
    ATTR_TABLE = SET_TO actueel = 0
    -> AttributeKeeper_2
AttributeKeeper_2
    KEEP_ATTRS = revisie,actueel,fase,tekeningnummer
    -> FeatureMerger_3 [SUPPLIER]
FeatureMerger_3
    SUPPLIERS_FIRST = No
    JOIN_KEYS = @Value(tekeningnummer) @Value(tekeningnummer) AUTO @Value(fase) @Value(fase) AUTO @Value(revisie) @Value(revisie) AUTO
    IGNORE_NULLS = No
    MERGE_TYPE = Attributes Only
    REJECT_NULL_MISSING_KEYS = No
    PROCESS_DUPS = No
    ATTR_ACCUM_MODE = Merge Supplier
    ATTR_CONFLICT_RES = Use Requestor
    MERGED -> Uit (output)
    <REJECTED> -> <Rejected> (output)
Uit (output)
<Rejected> (output)

Bookmark: aanmaken sorteerkenmerk
  We willen sorteren op fase, revisie. De ListSorter kan echter maar op 1 veld sorteren. 
  Daarom wordt hier fase en revisie gecombineerd tot "<fase>.<revisie>"; waarbij NULL-waardes als 0 worden beschouwd
AttributeCopier
    ATTR_TABLE:
      COPY fase > _fase
      COPY revisie > _revisie
    -> NullAttributeMapper
NullAttributeMapper
    NULL_TREATMENT = New Value
    NEW_VALUE = 0
    ATTRCHOICE = Selected Attributes
    SOURCE_ATTR_VAL = Null Empty "Missing (Selected Attributes Only)"
    ATTRLIST = _revisie _fase
    -> StringConcatenator
StringConcatenator
    VAL_ATTR = _faserevisie
    ACTION = Create New Attribute
    PARM_LINE = @Value(_fase).@Value(_revisie)
    -> ListBuilder

FME custom transformer tekeningMetadaExtractor
Extraheert bij elke tekening de gebiedscode, tekeningnummer, fase en revisie uit de naam van de bovenliggende folderstructuur.

Parameters:
- _TEKENINGPAD = @Value(_tekeningpad)   # Tekeningpad

In (input)
    -> AttributeSplitter
AttributeSplitter
    TRIM_OPTION = Both
    DROP_EMPTY_PARTS = No
    ATTR_NAME = _tekeningpad
    DELIMITER = \
    LIST_NAME = _directory
    -> ListIndexer_gebied
AttributeManager
    ATTR_TABLE:
      REMOVE _directory{}
      REMOVE gebied_directory
      REMOVE tekeningnummer_directory
      REMOVE _tekeningnrMatches{}.part
      REMOVE _tekeningnrMatches{}.startIndex
      RENAME_SET_VALUE tekeningnrpart > _tekeningnummer
      REMOVE tekeningnrstartIndex
      REMOVE _tekeningpad
      REMOVE fase_directory
      REMOVE revisie_directory
      REMOVE fasesubexpressies{}.part
      REMOVE fasesubexpressies{}.startIndex
      REMOVE fasepart
      REMOVE fasestartIndex
    -> Uit (output)
Uit (output)

Bookmark: bepalen gebiedcode
ListIndexer_gebied
    LIST_ATTR = _directory{}
    PREFIX = gebied
    INDEX = 6
    -> StringSearcher_gebied
    <REJECTED> -> Junction_9
StringSearcher_gebied
    CASE = no
    REGEXP = ^(\w{2,3})
    STRING_TO_SEARCH = @Value(gebied_directory)
    MATCHED_RESULT_ATTR = _gebiedcode
    MATCHED -> AttributeValueMapper
    NOT_MATCHED -> AttributeCreator_geenGebied
Note: IJS wordt YS
AttributeValueMapper
    DEFAULT_VALUE = @Value(_gebiedcode)
    VAL_ATTR = _gebiedcode
    LUT = IJS,YS
    DIRECTION = Forward (Source To Destination)
    SRC = _gebiedcode
    -> ListIndexer_tekeningnummer
AttributeCreator_geenGebied
    ATTR_TABLE = SET_TO uitvalreden = Tekening heeft geen gebiedcode.
    -> Junction
Junction
    -> Junction_2
Junction_9
    -> Junction_10

Bookmark: bepalen tekeningnummer
ListIndexer_tekeningnummer
    LIST_ATTR = _directory{}
    PREFIX = tekeningnummer
    INDEX = 7
    -> StringSearcher_tekeningnummer
    <REJECTED> -> Junction_5
StringSearcher_tekeningnummer
    MATCHED_PARTS_ATTR = _tekeningnrMatches
    CASE = no
    REGEXP = ^IP\s?(\d{2}-\d{4,8})
    STRING_TO_SEARCH = @Value(tekeningnummer_directory)
    MATCHED -> ListIndexer
    NOT_MATCHED -> AttributeValueMapper_2
ListIndexer
    LIST_ATTR = _tekeningnrMatches{}
    PREFIX = tekeningnr
    INDEX = 0
    -> ListIndexer_OUTPUT_-__ListIndexer_fase_2
    <REJECTED> -> Junction_11
Junction_11
    -> Junction_12
Note: specifieke uitzonderingen behandelen: / was / wordt / IP12-08-16-RO-Platenbuurt / <negeren> / IPs257-123-KC-Omg. Blok F - Park / s257-123 / IPs257-127-KC-Omg. Blok E Catharina van Zoelenstr / s257-127 / IP99-W-1588-HO-Meeuwenplaat-Steurweg / 99-W-1588 / IP92-W-2157-HO-Westpunt Tijmweg en Hofjes / 92-W-2157 / IP92-W-2148-HO-Troubadourlaan-Falstaffstr / 92-W-2148 / IP12-08-16-RO-Platenbuurt / 12-08-16
AttributeValueMapper_2
    VAL_ATTR = _tekeningnummer
    LUT = IP92-W-2148-HO-Troubadourlaan-Falstaffstr,92-W-2148,IP92-W-2157-HO-Westpunt Tijmweg en Hofjes,92-W-2157,IP99-W-1588-HO-Meeuwenplaat-Steurweg,99-W-1588,IPs257-123-KC-Omg. Blok F - Park,s257-123,IPs257-127-KC-Omg. Blok E Catharina van Zoelenstr,s257-127,IP12-08-16-RO-Platenbuurt,12-08-16
    DIRECTION = Forward (Source To Destination)
    SRC = tekeningnummer_directory
    -> Tester
Tester
    TEST_MODE = Automatic
    TEST_DESCRIPTION = ""
    BOOL_OP = OR
    TEST_CLAUSE = TEST @Value(_tekeningnummer) ATTRIBUTE_HAS_VALUE ""
    PASSED -> ListIndexer_OUTPUT_-__ListIndexer_fase_2
    FAILED -> AttributeCreator_geenTekeningnummmer
ListIndexer_OUTPUT_-__ListIndexer_fase_2: Junction
    -> ListIndexer_fase_2
AttributeCreator_geenTekeningnummmer
    ATTR_TABLE = SET_TO uitvalreden = Tekening heeft geen tekeningnummer.
    -> Junction_3
Junction_3
    -> Junction_4
Junction_5
    -> Junction_6

Bookmark: uitval
Junction_12
    -> _Rejected_ (output)
Junction_20
    -> _Rejected_ (output)
Junction_14
    -> _Rejected_ (output)
Junction_18
    -> Uitval (output)
Junction_8
    -> _Rejected_ (output)
Junction_4
    -> Uitval (output)
Junction_6
    -> _Rejected_ (output)
Junction_2
    -> Uitval (output)
Uitval (output)
Junction_10
    -> _Rejected_ (output)
_Rejected_ (output)

Bookmark: bepalen fase
ListIndexer_fase_2
    LIST_ATTR = _directory{}
    PREFIX = fase
    INDEX = 8
    -> StringSearcher_fase
    <REJECTED> -> Junction_7
Note: PVE(1/2/3) worden genegeerd.
StringSearcher_fase
    MATCHED_PARTS_ATTR = fasesubexpressies
    CASE = no
    REGEXP = ^\d{1,3}\s(\w{3,4})
    STRING_TO_SEARCH = @Value(fase_directory)
    MATCHED -> ListIndexer_2
    NOT_MATCHED -> AttributeCreator_geenFase_revisie
ListIndexer_2
    LIST_ATTR = fasesubexpressies{}
    PREFIX = fase
    INDEX = 0
    -> AttributeValueMapper_fase
    <REJECTED> -> Junction_13
AttributeValueMapper_fase
    VAL_ATTR = _fase
    LUT = VUZ,2,LVUZ,3,GUZ,4,DUZ,5,WUZ,6
    DIRECTION = Forward (Source To Destination)
    SRC = fasepart
    -> ListIndexer_revisie_2
Junction_13
    -> Junction_14
AttributeCreator_geenFase_revisie
    ATTR_TABLE = SET_TO uitvalreden = Tekening heeft geen fase.
    -> Junction_17
Junction_17
    -> Junction_18
Junction_7
    -> Junction_8

Bookmark: bepalen revisie indien aanwezig; anders op 1 zetten
ListIndexer_revisie_2
    LIST_ATTR = _directory{}
    PREFIX = revisie
    INDEX = 9
    -> StringSearcher_revisie
    <REJECTED> -> Junction_19
StringSearcher_revisie
    CASE = no
    REGEXP = (\d{1,2})$
    STRING_TO_SEARCH = @Value(revisie_directory)
    MATCHED_RESULT_ATTR = _revisie
    MATCHED -> StringSearcher_revisie_MATCHED_-__AttributeManager
    NOT_MATCHED -> AttributeCreator_revisie1
AttributeCreator_revisie1
    ATTR_TABLE = SET_TO _revisie = 1
    -> StringSearcher_revisie_MATCHED_-__AttributeManager
StringSearcher_revisie_MATCHED_-__AttributeManager: Junction
    -> AttributeManager
Junction_19
    -> Junction_20

FME custom transformer GUIDGenerator
Creates an ESRI GUID ID by creating a UUID enclosed by curly {}.
Input Ports
    Input
Accepts all types of features
    Output Ports
    Output
Returns all features with an additional GFID attribute

INPUT (input)
    -> UUIDGENERATOR_2
Note: Create UUID
UUIDGENERATOR_2: UUIDGenerator
    UUID_ATTR = GFID
    -> CONCATENATOR_2
Note: Enclose the UUID by {}
CONCATENATOR_2: StringConcatenator
    VAL_ATTR = GFID
    ACTION = Create New Attribute
    PARM_LINE = {@Value(GFID)}
    -> OUTPUT (output)
OUTPUT (output)

FME custom transformer VlakDissolverEnClipper
Voegt vakken samen. Een vak kan voor 100% meetellen of voor 50% (bijvoorbeeld een grasvlak versus half verhard). 
Als een vlak met 100%  overlapt met een vlak dat voor 50% meetelt, dan wint daar het vlak dat voor 50% meetelt.
Het kenmerk '_factor' geeft aan of het vlak 100% meetelt of voor 50% (_factor = 1 resp. 0.5)

Parameters:
- IDENTIFICATIE = @Value(identificatie)   # identificatie
- GROUP_BY = identificatie   # " " Group By

Heel (input)
    -> AttributeCreator_factorHeel
CoordinateRounder_Heel
    XPREC = 3
    ZPREC = 0
    YPREC = 3
    ROUNDED -> Dissolver_Heel
Dissolver_Heel
    GROUP_BY = $(GROUP_BY)
    CONNECT_Z_MODE = First Wins
    NO_OVRLP = No
    ACCUM_INPUT_ATTRS = Use Attributes From One Feature
    DEAGGREGATE_INPUT = Yes
    AREA -> Clipper_HeelHalf [CLIPPEE]
    <REJECTED> -> Junction_3
Junction_3
    -> Junction_4
Junction_4
    -> <Rejected> (output)
Half (input)
    -> AttributeCreator_factorHalf
CoordinateRounder_Half
    XPREC = 3
    ZPREC = 0
    YPREC = 3
    ROUNDED -> Dissolver_Half
Dissolver_Half
    GROUP_BY = identificatie
    CONNECT_Z_MODE = First Wins
    NO_OVRLP = No
    ACCUM_INPUT_ATTRS = Use Attributes From One Feature
    DEAGGREGATE_INPUT = Yes
    AREA -> Clipper_HeelHalf [CLIPPER]
    AREA -> Uit (output)
    <REJECTED> -> Junction_5
Note: Als een vlak halfgroen / overlapt met een vlak 100% / groen, dan wint halfgroen het.
Clipper_HeelHalf
    BOUNDARY_CASES = Treat as Inside
    LINES_AS_SEGMENTS = No
    PRESERVE_CLIPPEE_EXTENTS = No
    VAL_SOURCE = Clippee Only
    MEASURE_TYPE = Continuous
    MISSING_VAL_MODE = Compute
    CREATE_AGGREGATES = Yes
    CLIP_TYPE = Multiple Clippers
    OUTSIDE -> Uit (output)
    <REJECTED> -> Junction
Junction
    -> Junction_2
Junction_2
    -> <Rejected> (output)
Uit (output)
Junction_5
    -> Junction_6
Junction_6
    -> <Rejected> (output)
<Rejected> (output)

Bookmark: toekennen kenmerk '_factor'
AttributeCreator_factorHeel
    ATTR_TABLE = SET_TO _factor = 1
    -> CoordinateRounder_Heel
AttributeCreator_factorHalf
    ATTR_TABLE = SET_TO _factor = 0.5
    -> CoordinateRounder_Half

FME custom transformer OppervlaktetotaalBerekenaar
Bepaalt per tekningnummer, fase en rivisie het totale oppervlakte, rekening houdend met een vermenigvuldigingsfactor.

Parameters:
- _FACTOR = @Value(_factor)   # Factor
- IDENTIFICATIE = @Value(identificatie)   # identificatie

IN (input)
    -> AreaCalculator
Note: oppervlakte * factor / groen: factor = 1 / half groen: factor = 0.5
AreaCalculator
    AREA_TYPE = Plane Area
    AREA_ATTR = _area
    MULT = @Value(_factor)
    -> StatisticsCalculator
    <REJECTED> -> Junction_3
StatisticsCalculator
    GROUP_BY = identificatie
    SUM_ATTR = opp_m2
    COMPUTE_HISTOGRAM = NO
    PREPEND_ATTR_NAME_CHOICE = For multiple results only
    STATS_ATTRS = _area
    SUMMARY -> AttributeRounder
AttributeRounder
    PLACES = 0
    ROUND_TYPE = Nearest
    SRC_ATTRS = opp_m2
    -> Uit (output)
    <REJECTED> -> Junction
Uit (output)
Junction
    -> Junction_2
Junction_2
    -> <Rejected> (output)
Junction_3
    -> Junction_4
Junction_4
    -> <Rejected> (output)
<Rejected> (output)
